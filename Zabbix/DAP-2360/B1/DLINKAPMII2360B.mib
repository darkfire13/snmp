DAP-2360B-v206					DEFINITIONS ::= BEGIN

            IMPORTS
                private, IpAddress, TimeTicks   FROM    RFC1155-SMI
                ifIndex                         FROM    RFC1213-MIB
                OBJECT-TYPE                     FROM    RFC-1212
--              TruthValue                      FROM    SNMPv2-TC
                MacAddress                      FROM    SNMPv2-TC
                NOTIFICATION-TYPE,Counter64     FROM    SNMPv2-SMI;

            DisplayString ::= OCTET STRING
            -- This data type is used to model textual information taken
            -- from the NVT ASCII character set.  By convention, objects
            -- with this syntax are declared as having
            --
            -- SIZE(0..255)

            enterprises                             OBJECT  IDENTIFIER ::= { private 1 }
            dlink                                   OBJECT  IDENTIFIER ::= { enterprises 171 }
            dlink-products                          OBJECT  IDENTIFIER ::= { dlink 10 }
            dlink-dapfamily                         OBJECT  IDENTIFIER ::= { dlink-products 37 }
            -- dapfamily means D-Link wireless family

            dap2360B                                 OBJECT  IDENTIFIER ::= { dlink-dapfamily 50 }

            interface                               OBJECT  IDENTIFIER ::= { dap2360B 2 }

            lan                                     OBJECT  IDENTIFIER ::= { interface 1 }

            lanIfSetting                            OBJECT  IDENTIFIER ::= { lan 1 }

            lanIfSettingTable                       OBJECT-TYPE
            SYNTAX                                  SEQUENCE OF LanIfSettingEntry
            ACCESS                                  not-accessible
            STATUS                                  mandatory
            DESCRIPTION
            ""
            ::= { lanIfSetting 1 }

            lanIfSettingEntry                       OBJECT-TYPE
            SYNTAX                                  LanIfSettingEntry
            ACCESS                                  not-accessible
            STATUS                                  mandatory
            DESCRIPTION
            ""
            INDEX                                   {ifIndex}
            ::= { lanIfSettingTable 1 }

            LanIfSettingEntry
            ::= SEQUENCE
            {
                lanIfGetIpAddressFrom                   INTEGER,
                lanIfIpAddress                          IpAddress,
                lanIfSubnetMask                         IpAddress,
                lanIfDefaultGateway                     IpAddress,
                lanIfMacAddress                         MacAddress,
                lanIfPrimaryDNS                         IpAddress
 --              lanIfSecondaryDNS                       IpAddress
            }

            lanIfGetIpAddressFrom                   OBJECT-TYPE
            SYNTAX                                  INTEGER {static(1), dynamic(2)}
            ACCESS                                  read-write
            STATUS                                  mandatory
            DESCRIPTION
            ""
            ::= { lanIfSettingEntry 1 }

            lanIfIpAddress                          OBJECT-TYPE
            SYNTAX                                  IpAddress
            ACCESS                                  read-write
            STATUS                                  mandatory
            DESCRIPTION
            ""
            ::= { lanIfSettingEntry 2 }

            lanIfSubnetMask                         OBJECT-TYPE
            SYNTAX                                  IpAddress
            ACCESS                                  read-write
            STATUS                                  mandatory
            DESCRIPTION
            ""
            ::= { lanIfSettingEntry 3 }

            lanIfDefaultGateway                     OBJECT-TYPE
            SYNTAX                                  IpAddress
            ACCESS                                  read-write
            STATUS                                  mandatory
            DESCRIPTION
            ""
            ::= { lanIfSettingEntry 4 }

            lanIfMacAddress                         OBJECT-TYPE
            SYNTAX                                  MacAddress
            ACCESS                                  read-only
            STATUS                                  mandatory
            DESCRIPTION
            ""
            ::= { lanIfSettingEntry 5 }

            lanIfPrimaryDNS                         OBJECT-TYPE
            SYNTAX                                  IpAddress
            ACCESS                                  read-write
            STATUS                                  mandatory
            DESCRIPTION
            ""
            ::= { lanIfSettingEntry 6 }

 --           lanIfSecondaryDNS                       OBJECT-TYPE
 --           SYNTAX                                  IpAddress
 --           ACCESS                                  read-write
 --           STATUS                                  mandatory
 --           DESCRIPTION
 --           ""
 --           ::= { lanIfSettingEntry 7 }

 --           wiredLan                                OBJECT  IDENTIFIER ::= { lan 2 }

 --           wiredLanIfNumber                        OBJECT-TYPE
 --           SYNTAX                                  INTEGER
 --           ACCESS                                  read-only
 --           STATUS                                  mandatory
 --           DESCRIPTION
 --           ""
 --           ::= { wiredLan 1 }

 --           wiredLanIfTable                         OBJECT-TYPE
 --           SYNTAX                                  SEQUENCE OF WiredLanIfEntry
 --           ACCESS                                  not-accessible
 --           STATUS                                  mandatory
 --           DESCRIPTION
 --           ""
 --           ::= { wiredLan 2 }

 --           wiredLanIfEntry                         OBJECT-TYPE
 --           SYNTAX                                  WiredLanIfEntry
 --           ACCESS                                  not-accessible
 --           STATUS                                  mandatory
 --           DESCRIPTION
 --           ""
 --           INDEX                                   { ifIndex }
 --           ::= { wiredLanIfTable 1 }

 --           WiredLanIfEntry
 --           ::= SEQUENCE {
 --               wiredLanIfDesc                          OCTET STRING,
 --               wiredLanIfObjectID                      OBJECT IDENTIFIER
 --          }

 --           wiredLanIfDesc                          OBJECT-TYPE
 --          SYNTAX                                  OCTET STRING
 --           ACCESS                                  read-write
 --           STATUS                                  mandatory
 --           DESCRIPTION
 --           ""
 --           ::= { wiredLanIfEntry 1 }

 --           wiredLanIfObjectID                      OBJECT-TYPE
 --           SYNTAX                                  OBJECT IDENTIFIER
 --           ACCESS                                  read-only
 --           STATUS                                  mandatory
 --           DESCRIPTION
 --           ""
 --           ::= { wiredLanIfEntry 2 }

  --          ieee802dot3                             OBJECT  IDENTIFIER ::= { wiredLan 3 }

  --          dot3Parameters                          OBJECT  IDENTIFIER ::= { ieee802dot3 1 }

  --          dot3Securities                          OBJECT  IDENTIFIER ::= { ieee802dot3 2 }

  --          dot3Filter                              OBJECT  IDENTIFIER ::= { dot3Securities 1 }

  --          dot3MacAccessControlTable               OBJECT-TYPE
  --          SYNTAX                                  SEQUENCE OF Dot3MacAccessControlEntry
  --          ACCESS                                  not-accessible
  --          STATUS                                  mandatory
  --          DESCRIPTION
  --          ""
  --          ::= { dot3Filter 1 }

  --          dot3MacAccessControlEntry               OBJECT-TYPE
  --          SYNTAX                                  Dot3MacAccessControlEntry
  --          ACCESS                                  not-accessible
  --          STATUS                                  mandatory
  --          DESCRIPTION
  --          ""
  --          INDEX                                   {ifIndex}
  --          ::= { dot3MacAccessControlTable 1 }

  --          Dot3MacAccessControlEntry
  --          ::= SEQUENCE {
  --              dot3MacAccessControl                    INTEGER
   --         }

  --          dot3MacAccessControl                    OBJECT-TYPE
  --          SYNTAX                                  INTEGER { accept(1),
  --                                                            reject(2),
  --                                                           disabled(3)}
  --          ACCESS                                  read-write
  --          STATUS                                  mandatory
  --          DESCRIPTION
  --          ""
  --          ::= { dot3MacAccessControlEntry 1 }

  --          dot3MacAccessControlListTable           OBJECT-TYPE
  --          SYNTAX                                  SEQUENCE OF Dot3MacAccessControlListEntry
  --          ACCESS                                  not-accessible
  --          STATUS                                  mandatory
  --          DESCRIPTION
  --          ""
  --          ::= { dot3Filter 2 }

  --          dot3MacAccessControlListEntry           OBJECT-TYPE
 --           SYNTAX                                  Dot3MacAccessControlListEntry
 --           ACCESS                                  not-accessible
 --           STATUS                                  mandatory
 --           DESCRIPTION
 --           ""
 --           INDEX                                   {ifIndex, dot3MacAccessControlListIndex}
 --           ::= { dot3MacAccessControlListTable 1 }

 --           Dot3MacAccessControlListEntry
 --           ::= SEQUENCE {
 --               dot3MacAccessControlListIndex           INTEGER,
 --               dot3MacAccessControlListMacAddress      MacAddress
 --           }

 --           dot3MacAccessControlListIndex           OBJECT-TYPE
 --           SYNTAX                                  INTEGER (1..16)
 --           ACCESS                                  not-accessible
 --           STATUS                                  mandatory
 --           DESCRIPTION
 --           ""
 --           ::= { dot3MacAccessControlListEntry 1 }

 --           dot3MacAccessControlListMacAddress      OBJECT-TYPE
 --           SYNTAX                                  MacAddress
 --           ACCESS                                  read-write
 --           STATUS                                  mandatory
 --           DESCRIPTION
 --           ""
 --           ::= { dot3MacAccessControlListEntry 2 }

 --           dot3IpAccessControlTable                OBJECT-TYPE
 --           SYNTAX                                  SEQUENCE OF Dot3IpAccessControlEntry
 --           ACCESS                                  not-accessible
 --           STATUS                                  mandatory
 --           DESCRIPTION
  --          ""
 --           ::= { dot3Filter 3 }

 --           dot3IpAccessControlEntry                OBJECT-TYPE
 --           SYNTAX                                  Dot3IpAccessControlEntry
 --           ACCESS                                  not-accessible
 --           STATUS                                  mandatory
 --           DESCRIPTION
 --           ""
 --           INDEX                                   {ifIndex}
 --           ::= { dot3IpAccessControlTable 1 }

--            Dot3IpAccessControlEntry
 --           ::= SEQUENCE {
 --               dot3IpAccessControl                     INTEGER
 --           }

 --           dot3IpAccessControl                     OBJECT-TYPE
 --           SYNTAX                                  INTEGER { accept(1),
 --                                                             reject(2),
 --                                                             disabled(3)}
 --           ACCESS                                  read-write
 --           STATUS                                  mandatory
 --           DESCRIPTION
 --           ""
 --           ::= { dot3IpAccessControlEntry 1 }

 --           dot3IpAccessControlListTable            OBJECT-TYPE
 --           SYNTAX                                  SEQUENCE OF Dot3IpAccessControlListEntry
 --           ACCESS                                  not-accessible
 --           STATUS                                  mandatory
 --           DESCRIPTION
 --           ""
 --           ::= { dot3Filter 4 }

 --           dot3IpAccessControlListEntry            OBJECT-TYPE
 --           SYNTAX                                  Dot3IpAccessControlListEntry
 --           ACCESS                                  not-accessible
 --           STATUS                                  mandatory
 --           DESCRIPTION
 --           ""
 --           INDEX                                   {ifIndex, dot3IpAccessControlListIndex}
 --           ::= { dot3IpAccessControlListTable 1 }

 --           Dot3IpAccessControlListEntry
 --           ::= SEQUENCE {
 --               dot3IpAccessControlListIndex            INTEGER,
 --               dot3IpAccessControlListMacAddress      IpAddress
 --           }

 --           dot3IpAccessControlListIndex            OBJECT-TYPE
 --           SYNTAX                                  INTEGER (1..16)
 --           ACCESS                                  not-accessible
 --           STATUS                                  mandatory
 --           DESCRIPTION
 --           ""
 --          ::= { dot3IpAccessControlListEntry 1 }

 --           dot3IpAccessControlListMacAddress       OBJECT-TYPE
 --           SYNTAX                                  IpAddress
 --           ACCESS                                  read-write
 --           STATUS                                  mandatory
 --           DESCRIPTION
 --           ""
 --           ::= { dot3IpAccessControlListEntry 2 }

            wirelesslan                             OBJECT  IDENTIFIER ::= { lan 3 }

            wirelessLanIfNumber                     OBJECT-TYPE
            SYNTAX                                  INTEGER
            ACCESS                                  read-only
            STATUS                                  mandatory
            DESCRIPTION
            ""
            ::= { wirelesslan 1 }

            wirelessLanIfTable                      OBJECT-TYPE
            SYNTAX                                  SEQUENCE OF WirelessLanIfEntry
            ACCESS                                  not-accessible
            STATUS                                  mandatory
            DESCRIPTION
            ""
            ::= { wirelesslan 2 }

            wirelessLanIfEntry                      OBJECT-TYPE
            SYNTAX                                  WirelessLanIfEntry
            ACCESS                                  not-accessible
            STATUS                                  mandatory
            DESCRIPTION
            ""
            INDEX                                   {ifIndex}
            ::= { wirelessLanIfTable 1 }

            WirelessLanIfEntry
            ::= SEQUENCE
            {
                wirelessLanIfDesc                       OCTET STRING,
                wirelessLanIfObjectID                   OBJECT IDENTIFIER
            }

            wirelessLanIfDesc                       OBJECT-TYPE
            SYNTAX                                  OCTET STRING
            ACCESS                                  read-write
            STATUS                                  mandatory
            DESCRIPTION
            ""
            ::= { wirelessLanIfEntry 1 }

            wirelessLanIfObjectID                   OBJECT-TYPE
            SYNTAX                                  OBJECT IDENTIFIER
            ACCESS                                  read-only
            STATUS                                  mandatory
            DESCRIPTION
            ""
            ::= { wirelessLanIfEntry 2 }

            ieee802dot11                            OBJECT  IDENTIFIER ::= { wirelesslan 3 }

            dot11Parameters                         OBJECT  IDENTIFIER ::= { ieee802dot11 1 }

            dot11ParametersTable                    OBJECT-TYPE
            SYNTAX                                  SEQUENCE OF Dot11ParametersEntry
            ACCESS                                  not-accessible
            STATUS                                  mandatory
            DESCRIPTION
            ""
            ::= { dot11Parameters 1 }

            dot11ParametersEntry                    OBJECT-TYPE
            SYNTAX                                  Dot11ParametersEntry
            ACCESS                                  not-accessible
            STATUS                                  mandatory
            DESCRIPTION
            ""
            INDEX                                   {ifIndex}
            ::= { dot11ParametersTable 1 }

            Dot11ParametersEntry
            ::= SEQUENCE
            {
                dot11Ssid                               OCTET STRING,
                dot11SsidBroadcast                      INTEGER,
                dot11Channel                            INTEGER,
                dot11ChannelList                        OCTET STRING,
                -- dot11DynamicChannelList                 OCTET STRING,
                -- dot11StaticChannelList                  OCTET STRING,
                -- dot11WdsChannelList                     OCTET STRING,
                -- dot11WdsDynamicChannelList              OCTET STRING,
                -- dot11WdsStaticChannelList               OCTET STRING,
                dot11Frequency                          OCTET STRING,
                dot11DataRate                           OCTET STRING,
          --      dot11aModeDataRateList                  OCTET STRING,
          --      dot11bModeDataRateList                  OCTET STRING,
          --      dot11gModeDataRateList                  OCTET STRING,
          --      dot11nModeDataRateList                  OCTET STRING,
                dot11WifiMode                           INTEGER,
                dot11BeaconInterval                     INTEGER,
                dot11Dtim                               INTEGER,
          --      dot11FragmentLength                     INTEGER,
          --      dot11RtsLength                          INTEGER,
                dot11TransmitPower                      INTEGER,
          --      dot11SuperMode                          INTEGER,
                dot11RadioWave                          INTEGER,
                dot11AutoChannelScan                    INTEGER,
                dot11Wmm                                INTEGER,
          --      dot11Preamble                           INTEGER,
          --      dot11Antenna                            INTEGER,
                dot11ApMode                             INTEGER,
                dot11ChannelWidth                       INTEGER,
                dot11DataRateList                       OCTET STRING,
                dot11AckTimeout                         INTEGER,
                dot11ShortGI                            INTEGER,
                dot11Igmpsnooping                       INTEGER,
                dot11Band                       		INTEGER,
       --         dot11Band5GHzDataRateList           	OCTET STRING,
       --         dot11Band5GHzWdsChannelList             OCTET STRING,
       --         dot11Band5GHzChannelList                OCTET STRING,
                dot11ApModeStatus           			OCTET STRING,
                dot11Countrycode           			    OCTET STRING,
                dot11Application						INTEGER,
       --         dot11Band5GHzOutdoorChannelList         OCTET STRING,
                dot11MulticastRateABandList             OCTET STRING,
                dot11MulticastRateGBandList             OCTET STRING,
                dot11MulticastRateABand                 OCTET STRING,
                dot11MulticastRateGBand                 OCTET STRING,
                dot11HT2040Coexistence                  INTEGER
            }

            dot11Ssid                               OBJECT-TYPE
            SYNTAX                                  OCTET STRING
            ACCESS                                  read-write
            STATUS                                  mandatory
            DESCRIPTION
            ""
            ::= { dot11ParametersEntry 1 }

            dot11SsidBroadcast                      OBJECT-TYPE
            SYNTAX                                  INTEGER {disabled(0), enabled(1)}
            ACCESS                                  read-write
            STATUS                                  mandatory
            DESCRIPTION
            ""
            ::= { dot11ParametersEntry 2 }

            dot11Channel                            OBJECT-TYPE
            SYNTAX                                  INTEGER
            ACCESS                                  read-write
            STATUS                                  mandatory
            DESCRIPTION
            ""
            ::= { dot11ParametersEntry 3 }

            dot11ChannelList                        OBJECT-TYPE
            SYNTAX                                  OCTET STRING
            ACCESS                                  read-only
            STATUS                                  mandatory
            DESCRIPTION
            ""
            ::= { dot11ParametersEntry 4 }

            -- dot11DynamicChannelList                 OBJECT-TYPE
            -- SYNTAX                                  OCTET STRING
            -- ACCESS                                  read-only
            -- STATUS                                  mandatory
            -- DESCRIPTION
            -- ""
            -- ::= { dot11ParametersEntry 5 }

            -- dot11StaticChannelList                  OBJECT-TYPE
            -- SYNTAX                                  OCTET STRING
            -- ACCESS                                  read-only
            -- STATUS                                  mandatory
            -- DESCRIPTION
            -- ""
            -- ::= { dot11ParametersEntry 6 }

            -- dot11WdsChannelList                     OBJECT-TYPE
            -- SYNTAX                                  OCTET STRING
            -- ACCESS                                  read-only
            -- STATUS                                  mandatory
            -- DESCRIPTION
            -- ""
            -- ::= { dot11ParametersEntry 7 }

            -- dot11WdsDynamicChannelList              OBJECT-TYPE
            -- SYNTAX                                  OCTET STRING
            -- ACCESS                                  read-only
            -- STATUS                                  mandatory
            -- DESCRIPTION
            -- ""
            -- ::= { dot11ParametersEntry 8 }

            -- dot11WdsStaticChannelList               OBJECT-TYPE
            -- SYNTAX                                  OCTET STRING
            -- ACCESS                                  read-only
            -- STATUS                                  mandatory
            -- DESCRIPTION
            -- ""
            -- ::= { dot11ParametersEntry 9 }

            dot11Frequency                          OBJECT-TYPE
            SYNTAX                                  OCTET STRING
            ACCESS                                  read-only
            STATUS                                  mandatory
            DESCRIPTION
            ""
            ::= { dot11ParametersEntry 10 }

            dot11DataRate                           OBJECT-TYPE
            SYNTAX                                  OCTET STRING
            ACCESS                                  read-write
            STATUS                                  mandatory
            DESCRIPTION
            ""
            ::= { dot11ParametersEntry 11 }

       --     dot11aModeDataRateList                  OBJECT-TYPE
       --     SYNTAX                                  OCTET STRING
       --     ACCESS                                  read-only
       --     STATUS                                  mandatory
       --     DESCRIPTION
       --     ""
       --     ::= { dot11ParametersEntry 12 }

       --     dot11bModeDataRateList                  OBJECT-TYPE
       --     SYNTAX                                  OCTET STRING
       --     ACCESS                                  read-only
       --     STATUS                                  mandatory
       --     DESCRIPTION
       --     ""
       --     ::= { dot11ParametersEntry 13 }

       --     dot11gModeDataRateList                  OBJECT-TYPE
       --     SYNTAX                                  OCTET STRING
       --     ACCESS                                  read-only
       --     STATUS                                  mandatory
       --     DESCRIPTION
       --     ""
       --     ::= { dot11ParametersEntry 14 }

       --     dot11nModeDataRateList                  OBJECT-TYPE
       --     SYNTAX                                  OCTET STRING
       --     ACCESS                                  read-only
       --     STATUS                                  mandatory
       --     DESCRIPTION
       --     ""
       --     ::= { dot11ParametersEntry 15 }

            dot11WifiMode                           OBJECT-TYPE
            SYNTAX                                  INTEGER {
 --           					band2dot4-b(0),
 --           					band2dot4-g(1),
                                                     band2dot4-n(2),
                                                     band2dot4-bg(3),
 --                                                    band2dot4-bn(4),
--                                                     band2dot4-gn(5), 
                                                     band2dot4-bgn(6),
                                                     band5-a(7),
                                                     band5-n(8),
                                                     band5-an(9)}
            ACCESS                                  read-write
            STATUS                                  mandatory
            DESCRIPTION
            ""
            ::= { dot11ParametersEntry 16 }

            dot11BeaconInterval                     OBJECT-TYPE
            SYNTAX                                  INTEGER (25..200)
            ACCESS                                  read-write
            STATUS                                  mandatory
            DESCRIPTION
            ""
            ::= { dot11ParametersEntry 17 }

            dot11Dtim                               OBJECT-TYPE
            SYNTAX                                  INTEGER (1..15)
            ACCESS                                  read-write
            STATUS                                  mandatory
            DESCRIPTION
            ""
            ::= { dot11ParametersEntry 18 }

--            dot11FragmentLength                     OBJECT-TYPE
--            SYNTAX                                  INTEGER (256..2346)
--            ACCESS                                  read-write
--            STATUS                                  mandatory
--            DESCRIPTION
--            ""
--            ::= { dot11ParametersEntry 19 }

--            dot11RtsLength                          OBJECT-TYPE
--            SYNTAX                                  INTEGER (256..2346)
--            ACCESS                                  read-write
--            STATUS                                  mandatory
--            DESCRIPTION
--            ""
--            ::= { dot11ParametersEntry 20 }

            dot11TransmitPower                      OBJECT-TYPE
            SYNTAX                                  INTEGER {full(1),
                                                             half(2),
                                                             quarter(3),
                                                             eighth(4)}
            ACCESS                                  read-write
            STATUS                                  mandatory
            DESCRIPTION
            ""
            ::= { dot11ParametersEntry 21 }

     --       dot11SuperMode                          OBJECT-TYPE
     --       SYNTAX                                  INTEGER {super(1),
     --                                                        static(2),
     --                                                        dynamic(3),
     --                                                        disabled(4)}
     --       ACCESS                                  read-write
     --       STATUS                                  mandatory
     --       DESCRIPTION
     --       ""
     --       ::= { dot11ParametersEntry 22 }

            dot11RadioWave                          OBJECT-TYPE
            SYNTAX                                  INTEGER {off(0), on(1)}
            ACCESS                                  read-write
            STATUS                                  mandatory
            DESCRIPTION
            ""
            ::= { dot11ParametersEntry 23 }

            dot11AutoChannelScan                    OBJECT-TYPE
            SYNTAX                                  INTEGER {disabled(0), enabled(1)}
            ACCESS                                  read-write
            STATUS                                  mandatory
            DESCRIPTION
            ""
            ::= { dot11ParametersEntry 24 }

            dot11Wmm                                OBJECT-TYPE
            SYNTAX                                  INTEGER {disabled(0), enabled(1)}
            ACCESS                                  read-write
            STATUS                                  mandatory
            DESCRIPTION
            ""
            ::= { dot11ParametersEntry 25 }

      --      dot11Preamble                           OBJECT-TYPE
      --      SYNTAX                                  INTEGER {long(0), short(1)}
      --      ACCESS                                  read-write
      --      STATUS                                  mandatory
      --      DESCRIPTION
      --      ""
      --      ::= { dot11ParametersEntry 26 }

      --      dot11Antenna                            OBJECT-TYPE
      --      SYNTAX                                  INTEGER {auto(0),
      --                                                       ant1(1),
      --                                                       ant2(2)}
      --      ACCESS                                  read-write
      --      STATUS                                  mandatory
      --      DESCRIPTION
      --      ""
      --      ::= { dot11ParametersEntry 27 }

            dot11ApMode                             OBJECT-TYPE
            SYNTAX                                  INTEGER {ap(1),
                                                             wdsWithAp(2),
                                                             wdsWithoutAp(3) ,
                                                             wirelessClient(4)}
            ACCESS                                  read-write
            STATUS                                  mandatory
            DESCRIPTION
            ""
            ::= { dot11ParametersEntry 28 }

            dot11ChannelWidth                       OBJECT-TYPE
            SYNTAX                                  INTEGER {cwm20MHz(1),
                                                             cwmAuto(2)}

            ACCESS read-write
            STATUS mandatory
            DESCRIPTION
            " 1:20M Hz ; 2:Auto 20/40M Hz"
            ::= { dot11ParametersEntry 29 }

            dot11DataRateList                       OBJECT-TYPE
            SYNTAX                                  OCTET STRING
            ACCESS                                  read-only
            STATUS                                  mandatory
            DESCRIPTION
            ""
            ::= { dot11ParametersEntry 30 }

            dot11AckTimeout                         OBJECT-TYPE
            SYNTAX                                  INTEGER
            ACCESS read-write
            STATUS mandatory
            DESCRIPTION
            ""
            ::= { dot11ParametersEntry 31 }

            dot11ShortGI                            OBJECT-TYPE
            SYNTAX                                  INTEGER {disabled(0), enabled(1)}
            ACCESS                                  read-write
            STATUS                                  mandatory
            DESCRIPTION
            ""
            ::= { dot11ParametersEntry 32 }

            dot11Igmpsnooping                       OBJECT-TYPE
            SYNTAX                                  INTEGER {disabled(0), enabled(1)}
            ACCESS                                  read-write
            STATUS                                  mandatory
            DESCRIPTION
            ""
            ::= { dot11ParametersEntry 33 }

             dot11Band                       		OBJECT-TYPE
            SYNTAX                                  INTEGER {band2dot4gHz(0), band5gHz(1)}
            ACCESS                                  read-write
            STATUS                                  mandatory
            DESCRIPTION
            ""
            ::= { dot11ParametersEntry 34 }   

        --    dot11Band5GHzDataRateList           	OBJECT-TYPE
        --    SYNTAX                                  OCTET STRING
        --    ACCESS                                  read-only
        --    STATUS                                  mandatory
        --    DESCRIPTION
        --    ""
        --    ::= { dot11ParametersEntry 35 }

	    --    dot11Band5GHzWdsChannelList             OBJECT-TYPE
        --    SYNTAX                                  OCTET STRING
        --    ACCESS                                  read-only
        --    STATUS                                  mandatory
        --    DESCRIPTION
        --    ""
        --    ::= { dot11ParametersEntry 36 }


        --    dot11Band5GHzChannelList                OBJECT-TYPE
        --    SYNTAX                                  OCTET STRING
        --    ACCESS                                  read-only
        --    STATUS                                  mandatory
        --    DESCRIPTION
        --    ""
        --    ::= { dot11ParametersEntry 37 }

             dot11ApModeStatus           			OBJECT-TYPE
            SYNTAX                                  OCTET STRING
            ACCESS                                  read-only
            STATUS                                  mandatory
            DESCRIPTION
            ""
            ::= { dot11ParametersEntry 38 }

            dot11Countrycode           			OBJECT-TYPE
            SYNTAX                                  OCTET STRING
            ACCESS                                  read-only
            STATUS                                  mandatory
            DESCRIPTION
            ""
            ::= { dot11ParametersEntry 39 } 
            
            dot11Application           			OBJECT-TYPE
            SYNTAX                                  INTEGER {disable(0),indoor(1),outdoor(2)}
            ACCESS                                  read-write
            STATUS                                  mandatory
            DESCRIPTION
            ""
            ::= { dot11ParametersEntry 40 }   
           
        --   dot11Band5GHzOutdoorChannelList                 OBJECT-TYPE
        --    SYNTAX                                  OCTET STRING
        --    ACCESS                                  read-only
        --    STATUS                                  mandatory
        --    DESCRIPTION
        --    ""
        --    ::= { dot11ParametersEntry 41 }

            dot11MulticastRateABandList                 OBJECT-TYPE
            SYNTAX                                  OCTET STRING
            ACCESS                                  read-only
            STATUS                                  mandatory
            DESCRIPTION
            ""
            ::= { dot11ParametersEntry 42 }  
            
            dot11MulticastRateGBandList                 OBJECT-TYPE
            SYNTAX                                  OCTET STRING
            ACCESS                                  read-only
            STATUS                                  mandatory
            DESCRIPTION
            ""
            ::= { dot11ParametersEntry 43 }
            
            dot11MulticastRateABand                 OBJECT-TYPE
            SYNTAX                                  OCTET STRING
            ACCESS                                  read-write
            STATUS                                  mandatory
            DESCRIPTION
            ""
            ::= { dot11ParametersEntry 44 }
            
            dot11MulticastRateGBand                  OBJECT-TYPE
            SYNTAX                                  OCTET STRING
            ACCESS                                  read-write
            STATUS                                  mandatory
            DESCRIPTION
            ""
            ::= { dot11ParametersEntry 45 }
            
            dot11HT2040Coexistence           			OBJECT-TYPE
            SYNTAX                                  INTEGER {disable(0),enable(1)}
            ACCESS                                  read-write
            STATUS                                  mandatory
            DESCRIPTION
            ""
            ::= { dot11ParametersEntry 49 }

            dot11RemoteApMacAddress                         OBJECT  IDENTIFIER ::= { dot11Parameters 2 }

            dot11RemoteApMacAddressTable            OBJECT-TYPE
            SYNTAX                                  SEQUENCE OF Dot11RemoteApMacAddressEntry
            ACCESS                                  not-accessible
            STATUS                                  mandatory
            DESCRIPTION
            ""
            ::= { dot11RemoteApMacAddress 1 }

            dot11RemoteApMacAddressEntry            OBJECT-TYPE
            SYNTAX                                  Dot11RemoteApMacAddressEntry
            ACCESS                                  not-accessible
            STATUS                                  mandatory
            DESCRIPTION
            ""
            INDEX                                   {ifIndex, dot11RemoteApMacAddressIndex}
            ::= { dot11RemoteApMacAddressTable 1 }

            Dot11RemoteApMacAddressEntry
            ::= SEQUENCE {
                dot11RemoteApMacAddressIndex        INTEGER,
                dot11RemoteApMacAddressList         MacAddress
            }

            dot11RemoteApMacAddressIndex            OBJECT-TYPE
            SYNTAX                                  INTEGER (1..8)
            ACCESS                                  not-accessible
            STATUS                                  mandatory
            DESCRIPTION
            ""
            ::= { dot11RemoteApMacAddressEntry 1 }

            dot11RemoteApMacAddressList             OBJECT-TYPE
            SYNTAX                                  MacAddress
            ACCESS                                  read-write
            STATUS                                  mandatory
            DESCRIPTION
            ""
            ::= { dot11RemoteApMacAddressEntry 2 }

            dot11RemoteApMacAddressAccessTable      OBJECT-TYPE
            SYNTAX                                  SEQUENCE OF Dot11RemoteApMacAddressAccessEntry
            ACCESS                                  not-accessible
            STATUS                                  mandatory
            DESCRIPTION
            ""
            ::= { dot11RemoteApMacAddress 2 }

            dot11RemoteApMacAddressAccessEntry      OBJECT-TYPE
            SYNTAX                                  Dot11RemoteApMacAddressAccessEntry
            ACCESS                                  not-accessible
            STATUS                                  mandatory
            DESCRIPTION
            ""
            INDEX                                   {ifIndex}
            ::= { dot11RemoteApMacAddressAccessTable 1 }

            Dot11RemoteApMacAddressAccessEntry
            ::= SEQUENCE {
                dot11RemoteApMacAddressAdd          MacAddress,
                dot11RemoteApMacAddressDelete       MacAddress,
                dot11RemoteApMacAddressDeleteAll    INTEGER
            }

            dot11RemoteApMacAddressAdd     			OBJECT-TYPE
            SYNTAX                                  MacAddress
            ACCESS                                  read-write
            STATUS                                  mandatory
            DESCRIPTION
            ""
            ::= { dot11RemoteApMacAddressAccessEntry 1 }

            dot11RemoteApMacAddressDelete	     	OBJECT-TYPE
            SYNTAX                                  MacAddress
            ACCESS                                  read-write
            STATUS                                  mandatory
            DESCRIPTION
            ""
            ::= { dot11RemoteApMacAddressAccessEntry 2 }

            dot11RemoteApMacAddressDeleteAll	   	OBJECT-TYPE
            SYNTAX                                  INTEGER {nothing(0), deleteall(1)}
            ACCESS                                  read-write
            STATUS                                  mandatory
            DESCRIPTION
            ""
            ::= { dot11RemoteApMacAddressAccessEntry 3 }

            dot11SiteSurvey                         OBJECT  IDENTIFIER ::= { dot11Parameters 3 }

            dot11SiteSurveyRefreshTable             OBJECT-TYPE
            SYNTAX                                  SEQUENCE OF Dot11SiteSurveyRefreshEntry
            ACCESS                                  not-accessible
            STATUS                                  mandatory
            DESCRIPTION
            ""
            ::= { dot11SiteSurvey 1 }

            dot11SiteSurveyRefreshEntry             OBJECT-TYPE
            SYNTAX                                  Dot11SiteSurveyRefreshEntry
            ACCESS                                  not-accessible
            STATUS                                  mandatory
            DESCRIPTION
            ""
            INDEX                                   {ifIndex}
            ::= { dot11SiteSurveyRefreshTable 1 }

            Dot11SiteSurveyRefreshEntry
            ::= SEQUENCE {
                dot11SiteSurveyRefresh                  INTEGER
            }

            dot11SiteSurveyRefresh                  OBJECT-TYPE
            SYNTAX                                  INTEGER {nothing(0), refresh(1)}
            ACCESS                                  read-write
            STATUS                                  mandatory
            DESCRIPTION
            ""
            ::= { dot11SiteSurveyRefreshEntry 1 }

            dot11SiteSurveyTable                    OBJECT-TYPE
            SYNTAX                                  SEQUENCE OF Dot11SiteSurveyEntry
            ACCESS                                  not-accessible
            STATUS                                  mandatory
            DESCRIPTION
            ""
            ::= { dot11SiteSurvey 2 }

            dot11SiteSurveyEntry                    OBJECT-TYPE
            SYNTAX                                  Dot11SiteSurveyEntry
            ACCESS                                  not-accessible
            STATUS                                  mandatory
            DESCRIPTION
            ""
            INDEX                                   {ifIndex, dot11SiteSurveyIndex}
            ::= { dot11SiteSurveyTable 1 }

            Dot11SiteSurveyEntry
            ::= SEQUENCE {
                dot11SiteSurveyIndex                    INTEGER,
                dot11SiteSurveyBssType                  OCTET STRING,
                dot11SiteSurveyChannel                  INTEGER,
                dot11SiteSurveyRssi                     INTEGER,
                dot11SiteSurveyBssid                    MacAddress,
                dot11SiteSurveyEncryption               OCTET STRING,
                dot11SiteSurveySsid                     OCTET STRING
           --     dot11SiteSurveyWirelessMode             INTEGER,
           --     dot11SiteSurveySupportWds               INTEGER
            }

            dot11SiteSurveyIndex                    OBJECT-TYPE
            SYNTAX                                  INTEGER
            ACCESS                                  not-accessible
            STATUS                                  mandatory
            DESCRIPTION
            ""
            ::= { dot11SiteSurveyEntry 1 }

            dot11SiteSurveyBssType                  OBJECT-TYPE
            SYNTAX                                  OCTET STRING
            ACCESS                                  read-only
            STATUS                                  mandatory
            DESCRIPTION
            ""
            ::= { dot11SiteSurveyEntry 2 }

            dot11SiteSurveyChannel                  OBJECT-TYPE
            SYNTAX                                  INTEGER
            ACCESS                                  read-only
            STATUS                                  mandatory
            DESCRIPTION
            ""
            ::= { dot11SiteSurveyEntry 3 }

            dot11SiteSurveyRssi                     OBJECT-TYPE
            SYNTAX                                  INTEGER
            ACCESS                                  read-only
            STATUS                                  mandatory
            DESCRIPTION
            ""
            ::= { dot11SiteSurveyEntry 4 }

            dot11SiteSurveyBssid                    OBJECT-TYPE
            SYNTAX                                  MacAddress
            ACCESS                                  read-only
            STATUS                                  mandatory
            DESCRIPTION
            ""
            ::= { dot11SiteSurveyEntry 5 }

            dot11SiteSurveyEncryption               OBJECT-TYPE
            SYNTAX                                  OCTET STRING
            ACCESS                                  read-only
            STATUS                                  mandatory
            DESCRIPTION
            ""
            ::= { dot11SiteSurveyEntry 6 }

            dot11SiteSurveySsid                     OBJECT-TYPE
            SYNTAX                                  OCTET STRING (SIZE(0..32))
            ACCESS                                  read-only
            STATUS                                  mandatory
            DESCRIPTION
            ""
            ::= { dot11SiteSurveyEntry 7 }

      --      dot11SiteSurveyWirelessMode             OBJECT-TYPE
      --      SYNTAX                                  INTEGER {dot11a(0), dot11b(2), dot11g(3), dot11(4)}
      --      ACCESS                                  read-only
      --      STATUS                                  mandatory
      --      DESCRIPTION
      --      ""
      --      ::= { dot11SiteSurveyEntry 8 }

      --      dot11SiteSurveySupportWds               OBJECT-TYPE
      --      SYNTAX                                  INTEGER
      --      ACCESS                                  read-only
      --     STATUS                                  mandatory
      --      DESCRIPTION
      --      ""
      --      ::= { dot11SiteSurveyEntry 9 }

            dot11WdsSiteSurvey                         OBJECT  IDENTIFIER ::= { dot11Parameters 4 }

            dot11WdsSiteSurveyRefreshTable           OBJECT-TYPE
            SYNTAX                                  SEQUENCE OF Dot11WdsSiteSurveyRefreshEntry
            ACCESS                                  not-accessible
            STATUS                                  mandatory
            DESCRIPTION
            ""
            ::= { dot11WdsSiteSurvey 1 }

            dot11WdsSiteSurveyRefreshEntry           OBJECT-TYPE
            SYNTAX                                  Dot11WdsSiteSurveyRefreshEntry
            ACCESS                                  not-accessible
            STATUS                                  mandatory
            DESCRIPTION
            ""
            INDEX                                   {ifIndex}
            ::= { dot11WdsSiteSurveyRefreshTable 1 }

            Dot11WdsSiteSurveyRefreshEntry
            ::= SEQUENCE {
                dot11WdsSiteSurveyRefresh                  INTEGER
            }

            dot11WdsSiteSurveyRefresh                  OBJECT-TYPE
            SYNTAX                                  INTEGER {nothing(0), refresh(1)}
            ACCESS                                  read-write
            STATUS                                  mandatory
            DESCRIPTION
            ""
            ::= { dot11WdsSiteSurveyRefreshEntry 1 }

            dot11WdsSiteSurveyTable                    OBJECT-TYPE
            SYNTAX                                  SEQUENCE OF Dot11WdsSiteSurveyEntry
            ACCESS                                  not-accessible
            STATUS                                  mandatory
            DESCRIPTION
            ""
            ::= { dot11WdsSiteSurvey 2 }

            dot11WdsSiteSurveyEntry                    OBJECT-TYPE
            SYNTAX                                  Dot11WdsSiteSurveyEntry
            ACCESS                                  not-accessible
            STATUS                                  mandatory
            DESCRIPTION
            ""
            INDEX                                   {ifIndex ,dot11WdsSiteSurveyIndex}
            ::= { dot11WdsSiteSurveyTable 1 }

            Dot11WdsSiteSurveyEntry
            ::= SEQUENCE {
                dot11WdsSiteSurveyIndex                    INTEGER,
                dot11WdsSiteSurveyChannel                  INTEGER,
                dot11WdsSiteSurveyMode                     INTEGER,
                dot11WdsSiteSurveyBssid                    MacAddress,
                dot11WdsSiteSurveyEncryption               OCTET STRING,
                dot11WdsSiteSurveySsid                     OCTET STRING
            }

            dot11WdsSiteSurveyIndex                  OBJECT-TYPE
            SYNTAX                                  INTEGER
            ACCESS                                  not-accessible
            STATUS                                  mandatory
            DESCRIPTION
            ""
            ::= { dot11WdsSiteSurveyEntry 1 }

            dot11WdsSiteSurveyChannel               OBJECT-TYPE
            SYNTAX                                  INTEGER
            ACCESS                                  read-only
            STATUS                                  mandatory
            DESCRIPTION
            ""
            ::= { dot11WdsSiteSurveyEntry 2 }

 			dot11WdsSiteSurveyMode					OBJECT-TYPE
            SYNTAX                                  INTEGER
            ACCESS                                  read-only
            STATUS                                  mandatory
            DESCRIPTION
            ""
            ::= { dot11WdsSiteSurveyEntry 3 }

            dot11WdsSiteSurveyBssid                 OBJECT-TYPE
            SYNTAX                                  MacAddress
            ACCESS                                  read-only
            STATUS                                  mandatory
            DESCRIPTION
            ""
            ::= { dot11WdsSiteSurveyEntry 4 }

            dot11WdsSiteSurveyEncryption            OBJECT-TYPE
            SYNTAX                                  OCTET STRING
            ACCESS                                  read-only
            STATUS                                  mandatory
            DESCRIPTION
            ""
            ::= { dot11WdsSiteSurveyEntry 5 }

            dot11WdsSiteSurveySsid                  OBJECT-TYPE
            SYNTAX                                  OCTET STRING (SIZE(0..32))
            ACCESS                                  read-only
            STATUS                                  mandatory
            DESCRIPTION
            ""
            ::= { dot11WdsSiteSurveyEntry 6 }     


            dot11Securities                         OBJECT  IDENTIFIER ::= { ieee802dot11 2 }

            dot11SecuritiesTable                    OBJECT-TYPE
            SYNTAX                                  SEQUENCE OF Dot11SecuritiesEntry
            ACCESS                                  not-accessible
            STATUS                                  mandatory
            DESCRIPTION
            ""
            ::= { dot11Securities 1 }

            dot11SecuritiesEntry                    OBJECT-TYPE
            SYNTAX                                  Dot11SecuritiesEntry
            ACCESS                                  not-accessible
            STATUS                                  mandatory
            DESCRIPTION
            ""
            INDEX                                   {ifIndex}
            ::= { dot11SecuritiesTable 1 }

            Dot11SecuritiesEntry
            ::= SEQUENCE
            {
                dot11Authentication                 INTEGER,
                dot11Encryption                     INTEGER,
                dot11KeyIndex                       INTEGER,
                dot11PassPhrase                     OCTET STRING,
                dot11CipherType                     INTEGER,
                dot11GroupKeyUpdateInterval         INTEGER,
             --   dot11KeyWepType		                INTEGER,
                dot11PrimaryRadiusServer           		IpAddress,
                dot11PrimaryRadiusPort             		INTEGER,
                dot11PrimaryRadiusSecret           		OCTET STRING,
--                dot11SecondaryRadiusServer         		IpAddress,
--                dot11SecondaryRadiusPort           		INTEGER,
--                dot11SecondaryRadiusSecret         		OCTET STRING,
--                dot11PrimaryAccountingStatus       		INTEGER,
--                dot11PrimaryAccountingServer       		IpAddress,
--                dot11PrimaryAccountingServerPort   		INTEGER,
--                dot11PrimaryAccountingPassPhrase   		OCTET STRING,
--                dot11SecondaryAccountingStatus       		INTEGER,
--                dot11SecondaryAccountingServer       		IpAddress,
--                dot11SecondaryAccountingServerPort   		INTEGER,
--                dot11SecondaryAccountingPassPhrase   		OCTET STRING,
                dot11NetworkAccessProtection             	INTEGER,
--		dot11RadiusSource                       	INTEGER,
		dot11RadiusKeyUpdateInterval			INTEGER,
		dot11WpaEapType			                INTEGER,
		dot11WpaEapAuthenticationType             	INTEGER,
		dot11WpaEapUsername                     	OCTET STRING,
		dot11WpaEapPasswd                       	OCTET STRING,
		dot11AutoRekeyControl                   	INTEGER,
		dot11AutoRekeyStartWeek                 	INTEGER,
		dot11AutoRekeyStartTime                 	OCTET STRING,
		dot11AutoRekeyTimeInterval              	INTEGER,
		dot11AutoRekeyPassPhrase     			OCTET STRING		
            }

            dot11Authentication                     OBJECT-TYPE
            SYNTAX                                  INTEGER {opensystem(1),
                                                             sharedkey(2),
                                                             opensystem-sharedkey(3),
                                                             wpa-psk(4),
                                                             wpa-eap(5),
                                                             wpa2-psk(6),
                                                             wpa2-eap(7),
                                                             wpa2-auto-psk(8),
                                                             wpa2-auto-eap(9),
                                                             dot1x(10)}
            ACCESS                                  read-write
            STATUS                                  mandatory
            DESCRIPTION
            ""
            ::= { dot11SecuritiesEntry 1 }


            dot11Encryption                         OBJECT-TYPE
            SYNTAX                                  INTEGER {disabled(0), enabled(1)}
            ACCESS                                  read-write
            STATUS                                  mandatory
            DESCRIPTION
            ""
            ::= { dot11SecuritiesEntry 2 }

            dot11KeyIndex                           OBJECT-TYPE
            SYNTAX                                  INTEGER {first(1),
                                                             second(2),
                                                             third(3),
                                                             fourth(4)}
            ACCESS read-write
            STATUS mandatory
            DESCRIPTION
            ""
            ::= { dot11SecuritiesEntry 3 }

            dot11PassPhrase                         OBJECT-TYPE
            SYNTAX                                  OCTET STRING (SIZE(8..63))
            ACCESS                                  read-write
            STATUS                                  mandatory
            DESCRIPTION
            ""
            ::= { dot11SecuritiesEntry 4 }

            dot11CipherType                         OBJECT-TYPE
            SYNTAX                                  INTEGER {auto(1), aes(2), tkip(3), wep(4)}
            ACCESS                                  read-write
            STATUS                                  mandatory
            DESCRIPTION
            ""
            ::= { dot11SecuritiesEntry 5 }

            dot11GroupKeyUpdateInterval             OBJECT-TYPE
            SYNTAX                                  INTEGER (300..9999999)
            ACCESS                                  read-write
            STATUS                                  mandatory
            DESCRIPTION
            ""
            ::= { dot11SecuritiesEntry 6 }

     --       dot11KeyWepType                         OBJECT-TYPE
     --       SYNTAX                                  INTEGER {static(0),dynamic(1)}
     --       ACCESS                                  read-write
     --       STATUS                                  mandatory
     --       DESCRIPTION
     --       ""
     --       ::= { dot11SecuritiesEntry 7 }

                      
            dot11PrimaryRadiusServer           		OBJECT-TYPE
            SYNTAX                                  IpAddress
            ACCESS                                  read-write
            STATUS                                  mandatory
            DESCRIPTION
            ""
            ::= { dot11SecuritiesEntry 8 }

            dot11PrimaryRadiusPort             		OBJECT-TYPE
            SYNTAX                                  INTEGER (0..65535)
            ACCESS                                  read-write
            STATUS                                  mandatory
            DESCRIPTION
            ""
            ::= { dot11SecuritiesEntry 9 }

            dot11PrimaryRadiusSecret           		OBJECT-TYPE
            SYNTAX                                  OCTET STRING (SIZE(0..32))
            ACCESS                                  read-write
            STATUS                                  mandatory
            DESCRIPTION
            ""
            ::= { dot11SecuritiesEntry 10 }   
            
--            dot11SecondaryRadiusServer         		OBJECT-TYPE
--            SYNTAX                                  IpAddress
--            ACCESS                                  read-write
--            STATUS                                  mandatory
--            DESCRIPTION
--            ""
--            ::= { dot11SecuritiesEntry 11 }

--            dot11SecondaryRadiusPort           		OBJECT-TYPE
--            SYNTAX                                  INTEGER (0..65535)
--            ACCESS                                  read-write
--            STATUS                                  mandatory
--            DESCRIPTION
--            ""
--           ::= { dot11SecuritiesEntry 12 }

--            dot11SecondaryRadiusSecret         		OBJECT-TYPE
--            SYNTAX                                  OCTET STRING (SIZE(0..32))
--            ACCESS                                  read-write
--            STATUS                                  mandatory
--            DESCRIPTION
--            ""
--            ::= { dot11SecuritiesEntry 13 }
            

--            dot11PrimaryAccountingStatus       		OBJECT-TYPE
--            SYNTAX                                  INTEGER {disabled(0), enabled(1)}
--            ACCESS                                  read-write
--            STATUS                                  mandatory
--            DESCRIPTION
--            ""
--            ::= { dot11SecuritiesEntry 14 }

--            dot11PrimaryAccountingServer       		OBJECT-TYPE
--            SYNTAX                                  IpAddress
--            ACCESS                                  read-write
--            STATUS                                  mandatory
--            DESCRIPTION
--            ""
--            ::= { dot11SecuritiesEntry 15 }

--            dot11PrimaryAccountingServerPort   		OBJECT-TYPE
--            SYNTAX                                  INTEGER
--            ACCESS                                  read-write
--            STATUS                                  mandatory
--            DESCRIPTION
--            ""
--            ::= { dot11SecuritiesEntry 16 }

--            dot11PrimaryAccountingPassPhrase   		OBJECT-TYPE
--            SYNTAX                                  OCTET STRING
--            ACCESS                                  read-write
--            STATUS                                  mandatory
--            DESCRIPTION
--            ""
--            ::= { dot11SecuritiesEntry 17 } 
            
--            dot11SecondaryAccountingStatus       	OBJECT-TYPE
--            SYNTAX                                  INTEGER {disabled(0), enabled(1)}
--            ACCESS                                  read-write
--            STATUS                                  mandatory
--            DESCRIPTION
--            ""
--            ::= { dot11SecuritiesEntry 18 }

--            dot11SecondaryAccountingServer       		OBJECT-TYPE
--            SYNTAX                                  	IpAddress
--            ACCESS                                  	read-write
--            STATUS                                  	mandatory
--            DESCRIPTION
--            ""
--            ::= { dot11SecuritiesEntry 19 }

--            dot11SecondaryAccountingServerPort   		OBJECT-TYPE
--            SYNTAX                                  	INTEGER
--            ACCESS                                  	read-write
--            STATUS                                  	mandatory
--            DESCRIPTION
--            ""
--            ::= { dot11SecuritiesEntry 20 }

--            dot11SecondaryAccountingPassPhrase			OBJECT-TYPE
--            SYNTAX                                  	OCTET STRING
--            ACCESS                                  	read-write
--            STATUS                                  	mandatory
--            DESCRIPTION
--            ""
--            ::= { dot11SecuritiesEntry 21 } 

            dot11NetworkAccessProtection   		OBJECT-TYPE
            SYNTAX                                  	INTEGER{disable(0), enable(1)}
            ACCESS                                  	read-write
            STATUS                                  	mandatory
            DESCRIPTION
            ""
            ::= { dot11SecuritiesEntry 22 }

--            dot11RadiusSource   		OBJECT-TYPE
--            SYNTAX                                  	INTEGER{remote(1), local(2)}
--            ACCESS                                  	read-write
--            STATUS                                  	mandatory
--            DESCRIPTION
--            ""
--            ::= { dot11SecuritiesEntry 23 }

            dot11RadiusKeyUpdateInterval   		OBJECT-TYPE
            SYNTAX                                  	INTEGER(300..9999999)
            ACCESS                                  	read-write
            STATUS                                  	mandatory
            DESCRIPTION
            ""
            ::= { dot11SecuritiesEntry 24 } 
                                                                                                                      
            dot11WpaEapType   		OBJECT-TYPE
            SYNTAX                                  	INTEGER{ttls(1), peap(2)}
            ACCESS                                  	read-write
            STATUS                                  	mandatory
            DESCRIPTION
            ""
            ::= { dot11SecuritiesEntry 25 }

            dot11WpaEapAuthenticationType   		OBJECT-TYPE
            SYNTAX                                  	INTEGER{mschapv2(2), pap(3),chap(4)}
            ACCESS                                  	read-write
            STATUS                                  	mandatory
            DESCRIPTION
            ""
            ::= { dot11SecuritiesEntry 26 }

            dot11WpaEapUsername   		OBJECT-TYPE
            SYNTAX                                  	OCTET STRING
            ACCESS                                  	read-write
            STATUS                                  	mandatory
            DESCRIPTION
            ""
            ::= { dot11SecuritiesEntry 27 }

            dot11WpaEapPasswd   		OBJECT-TYPE
            SYNTAX                                  	OCTET STRING
            ACCESS                                  	read-write
            STATUS                                  	mandatory
            DESCRIPTION
            ""
            ::= { dot11SecuritiesEntry 28 }   
            
            dot11AutoRekeyControl     					OBJECT-TYPE
            SYNTAX                                  	INTEGER{disable(0), enable(1)}
            ACCESS                                  	read-write
            STATUS                                  	mandatory
            DESCRIPTION
            "disable( Manual ) , enable(Periodrical Key Change )"
            ::= { dot11SecuritiesEntry 29 }  
            
            dot11AutoRekeyStartWeek     				OBJECT-TYPE
            SYNTAX                                  	INTEGER{sun(0),
                                                            mon(1),
                                                            tue(2),
                                                            wed(3),
                                                            thu(4),
                                                            fri(5),
                                                            sat(6)}
            ACCESS                                  	read-write
            STATUS                                  	mandatory
            DESCRIPTION
            ""
            ::= { dot11SecuritiesEntry 30 }   
            
            dot11AutoRekeyStartTime   					OBJECT-TYPE
            SYNTAX                                  	OCTET STRING
            ACCESS                                  	read-write
            STATUS                                  	mandatory
            DESCRIPTION
            " Please follow this format: 'xx:xx'
              For example: 23:45 "
            ::= { dot11SecuritiesEntry 31 }

            
            dot11AutoRekeyTimeInterval     			OBJECT-TYPE
            SYNTAX                                  	INTEGER(1..168)
            ACCESS                                  	read-write
            STATUS                                  	mandatory
            DESCRIPTION
            ""            
            ::= { dot11SecuritiesEntry 32 } 
            
            dot11AutoRekeyPassPhrase     			OBJECT-TYPE
            SYNTAX                                  	OCTET STRING
            ACCESS                                  	read-only
            STATUS                                  	mandatory
            DESCRIPTION
            ""            
            ::= { dot11SecuritiesEntry 33 }

            dot11WepKeyTable                        OBJECT-TYPE
            SYNTAX                                  SEQUENCE OF Dot11WepKeyEntry
            ACCESS                                  not-accessible
            STATUS                                  mandatory
            DESCRIPTION
            ""
            ::= { dot11Securities 2 }

            dot11WepKeyEntry                        OBJECT-TYPE
            SYNTAX                                  Dot11WepKeyEntry
            ACCESS                                  not-accessible
            STATUS                                  mandatory
            DESCRIPTION
            ""
            INDEX                                   {ifIndex, dot11wepKeyIndex}
            ::= { dot11WepKeyTable 1 }

            Dot11WepKeyEntry
            ::= SEQUENCE
            {
                dot11wepKeyIndex                    INTEGER,
                dot11WepKeyEntryMethod              INTEGER,
                dot11WepKey                         OCTET STRING,
                dot11wepKeyLength                    INTEGER
            }

            dot11wepKeyIndex                        OBJECT-TYPE
            SYNTAX                                  INTEGER (1..8)
            ACCESS                                  not-accessible
            STATUS                                  mandatory
            DESCRIPTION
            ""
            ::= { dot11WepKeyEntry 1 }

            dot11WepKeyEntryMethod                  OBJECT-TYPE
            SYNTAX                                  INTEGER {ascii(1), hex(2)}
            ACCESS                                  read-write
            STATUS                                  mandatory
            DESCRIPTION
            ""
            ::= { dot11WepKeyEntry 2 }

            dot11WepKey                             OBJECT-TYPE
            SYNTAX                                  OCTET STRING
            ACCESS                                  read-write
            STATUS                                  mandatory
            DESCRIPTION
            ""
            ::= { dot11WepKeyEntry  3 }
            dot11wepKeyLength                        OBJECT-TYPE
            SYNTAX                                  INTEGER
            ACCESS                                  read-only
            STATUS                                  mandatory
            DESCRIPTION
            ""
            ::= { dot11WepKeyEntry 4 }

            dot11Filter                             OBJECT  IDENTIFIER ::= { dot11Securities 3 }

            dot11PartionTable                       OBJECT-TYPE
            SYNTAX                                  SEQUENCE OF Dot11PartionEntry
            ACCESS                                  not-accessible
            STATUS                                  mandatory
            DESCRIPTION
            ""
            ::= { dot11Filter 1 }

            dot11PartionEntry                    OBJECT-TYPE
            SYNTAX                                  Dot11PartionEntry
            ACCESS                                  not-accessible
            STATUS                                  mandatory
            DESCRIPTION
            ""
            INDEX                                   {ifIndex}
            ::= { dot11PartionTable 1 }

            Dot11PartionEntry
            ::= SEQUENCE
            {
--                dot11InternalStationConnection             	  INTEGER,
                dot11EthernetToWlanAccess               	  INTEGER,
            --    dot11InternalStationConnectionBetweenIf 	  INTEGER,
                dot11InternalStationConnectionPrimarySSID         INTEGER,
                dot11InternalStationConnectionMultiSSID1          INTEGER,
                dot11InternalStationConnectionMultiSSID2          INTEGER,
                dot11InternalStationConnectionMultiSSID3          INTEGER,
                dot11InternalStationConnectionMultiSSID4          INTEGER,
                dot11InternalStationConnectionMultiSSID5          INTEGER,
                dot11InternalStationConnectionMultiSSID6          INTEGER,
                dot11InternalStationConnectionMultiSSID7          INTEGER                                                                

            }

--             dot11InternalStationConnection          OBJECT-TYPE
--            SYNTAX                                  INTEGER {disabled(0), enabled(1)}
--            ACCESS                                  read-write
--            STATUS                                  mandatory
--            DESCRIPTION
--            ""
--            ::= { dot11PartionEntry 1 }

            dot11EthernetToWlanAccess               OBJECT-TYPE
            SYNTAX                                  INTEGER {disable(0), enable(1)}
            ACCESS                                  read-write
            STATUS                                  mandatory
            DESCRIPTION
            ""
            ::= { dot11PartionEntry 2 }

      --      dot11InternalStationConnectionBetweenIf OBJECT-TYPE
      --      SYNTAX                                  INTEGER {disabled(0), enabled(1)}
      --      ACCESS                                  read-write
      --      STATUS                                  mandatory
      --      DESCRIPTION
      --      ""
      --      ::= { dot11PartionEntry 3 }

              dot11InternalStationConnectionPrimarySSID          OBJECT-TYPE
            SYNTAX                                  INTEGER {enable(0), disable(1),guestmode(2)}
            ACCESS                                  read-write
            STATUS                                  mandatory
            DESCRIPTION
            ""
            ::= { dot11PartionEntry 4 }

             dot11InternalStationConnectionMultiSSID1          OBJECT-TYPE
            SYNTAX                                  INTEGER {enable(0), disable(1),guestmode(2)}
            ACCESS                                  read-write
            STATUS                                  mandatory
            DESCRIPTION
            ""
            ::= { dot11PartionEntry 5 }
             dot11InternalStationConnectionMultiSSID2          OBJECT-TYPE
            SYNTAX                                  INTEGER {enable(0), disable(1),guestmode(2)}
            ACCESS                                  read-write
            STATUS                                  mandatory
            DESCRIPTION
            ""
            ::= { dot11PartionEntry 6 }
             dot11InternalStationConnectionMultiSSID3          OBJECT-TYPE
            SYNTAX                                  INTEGER {enable(0), disable(1),guestmode(2)}
            ACCESS                                  read-write
            STATUS                                  mandatory
            DESCRIPTION
            ""
            ::= { dot11PartionEntry 7 }
             dot11InternalStationConnectionMultiSSID4          OBJECT-TYPE
            SYNTAX                                  INTEGER {enable(0), disable(1),guestmode(2)}
            ACCESS                                  read-write
            STATUS                                  mandatory
            DESCRIPTION
            ""
            ::= { dot11PartionEntry 8 }
             dot11InternalStationConnectionMultiSSID5          OBJECT-TYPE
            SYNTAX                                  INTEGER {enable(0), disable(1),guestmode(2)}
            ACCESS                                  read-write
            STATUS                                  mandatory
            DESCRIPTION
            ""
            ::= { dot11PartionEntry 9 }
             dot11InternalStationConnectionMultiSSID6          OBJECT-TYPE
            SYNTAX                                  INTEGER {enable(0), disable(1),guestmode(2)}
            ACCESS                                  read-write
            STATUS                                  mandatory
            DESCRIPTION
            ""
            ::= { dot11PartionEntry 10 }
             dot11InternalStationConnectionMultiSSID7          OBJECT-TYPE
            SYNTAX                                  INTEGER {enable(0), disable(1),guestmode(2)}
            ACCESS                                  read-write
            STATUS                                  mandatory
            DESCRIPTION
            ""
            ::= { dot11PartionEntry 11 }


            dot11MacAccessControlTable              OBJECT-TYPE
            SYNTAX                                  SEQUENCE OF Dot11MacAccessControlEntry
            ACCESS                                  not-accessible
            STATUS                                  mandatory
            DESCRIPTION
            ""
            ::= { dot11Filter 2 }

            dot11MacAccessControlEntry              OBJECT-TYPE
            SYNTAX                                  Dot11MacAccessControlEntry
            ACCESS                                  not-accessible
            STATUS                                  mandatory
            DESCRIPTION
            ""
            INDEX                                   {ifIndex}
            ::= { dot11MacAccessControlTable 1 }

            Dot11MacAccessControlEntry
            ::= SEQUENCE {
                dot11MacAccessControl                   INTEGER,
                dot11MacAccessControlMacAddressAdd      MacAddress,
                dot11MacAccessControlMacAddressDelete   MacAddress
            }

            dot11MacAccessControl                   OBJECT-TYPE
            SYNTAX                                  INTEGER { accept(1),
                                                              reject(2),
                                                              disabled(3)}
            ACCESS                                  read-write
            STATUS                                  mandatory
            DESCRIPTION
            ""
            ::= { dot11MacAccessControlEntry 1 }

            dot11MacAccessControlMacAddressAdd     	OBJECT-TYPE
            SYNTAX                                  MacAddress
            ACCESS                                  read-write
            STATUS                                  mandatory
            DESCRIPTION
            ""
            ::= { dot11MacAccessControlEntry 2 }

            dot11MacAccessControlMacAddressDelete	OBJECT-TYPE
            SYNTAX                                  MacAddress
            ACCESS                                  read-write
            STATUS                                  mandatory
            DESCRIPTION
            ""
            ::= { dot11MacAccessControlEntry 3 }

            dot11MacAccessControlListTable          OBJECT-TYPE
            SYNTAX                                  SEQUENCE OF Dot11MacAccessControlListEntry
            ACCESS                                  not-accessible
            STATUS                                  mandatory
            DESCRIPTION
            ""
            ::= { dot11Filter 3 }

            dot11MacAccessControlListEntry          OBJECT-TYPE
            SYNTAX                                  Dot11MacAccessControlListEntry
            ACCESS                                  not-accessible
            STATUS                                  mandatory
            DESCRIPTION
            ""
            INDEX                                   {ifIndex, dot11MacAccessControlListIndex}
            ::= { dot11MacAccessControlListTable 1 }

            Dot11MacAccessControlListEntry
            ::= SEQUENCE {
                dot11MacAccessControlListIndex          INTEGER,
                dot11MacAccessControlListMacAddress     MacAddress
            }

            dot11MacAccessControlListIndex          OBJECT-TYPE
            SYNTAX                                  INTEGER (1..16)
            ACCESS                                  not-accessible
            STATUS                                  mandatory
            DESCRIPTION
            ""
            ::= { dot11MacAccessControlListEntry 1 }

            dot11MacAccessControlListMacAddress     OBJECT-TYPE
            SYNTAX                                  MacAddress
            ACCESS                                  read-write
            STATUS                                  mandatory
            DESCRIPTION
            ""
            ::= { dot11MacAccessControlListEntry 2 }

     --       dot11IpAccessControlTable               OBJECT-TYPE
     --       SYNTAX                                  SEQUENCE OF Dot11IpAccessControlEntry
     --       ACCESS                                  not-accessible
     --       STATUS                                  mandatory
     --       DESCRIPTION
     --       ""
     --       ::= { dot11Filter 4 }

     --       dot11IpAccessControlEntry               OBJECT-TYPE
     --       SYNTAX                                  Dot11IpAccessControlEntry
     --       ACCESS                                  not-accessible
     --       STATUS                                  mandatory
     --       DESCRIPTION
     --       ""
     --       INDEX                                   {ifIndex}
     --       ::= { dot11IpAccessControlTable 1 }

     --       Dot11IpAccessControlEntry
     --       ::= SEQUENCE {
     --           dot11IpAccessControl                    INTEGER
     --       }

     --       dot11IpAccessControl                    OBJECT-TYPE
     --       SYNTAX                                  INTEGER { accept(1),
     --                                                         reject(2),
     --                                                         disabled(3)}
     --       ACCESS                                  read-write
      --      STATUS                                  mandatory
     --       DESCRIPTION
     --       ""
     --       ::= { dot11IpAccessControlEntry 1 }

    --        dot11IpAccessControlListTable           OBJECT-TYPE
    --        SYNTAX                                  SEQUENCE OF Dot11IpAccessControlListEntry
    --        ACCESS                                  not-accessible
    --        STATUS                                  mandatory
    --        DESCRIPTION
    --        ""
    --        ::= { dot11Filter 5 }

    --        dot11RADIUSTable                        OBJECT-TYPE
    --        SYNTAX                                  SEQUENCE OF Dot11RADIUSEntry
    --        ACCESS                                  not-accessible
    --        STATUS                                  mandatory
    --        DESCRIPTION
    --        ""
    --        ::= { dot11Securities 4 }

    --        dot11RADIUSEntry                        OBJECT-TYPE
    --        SYNTAX                                  Dot11RADIUSEntry
    --        ACCESS                                  not-accessible
    --        STATUS                                  mandatory
    --        DESCRIPTION
    --        ""
    --        INDEX                                   {dot11RADIUSIndex}
    --        ::= { dot11RADIUSTable 1 }

    --        Dot11RADIUSEntry
    --        ::= SEQUENCE
    --        {
    --            dot11RADIUSIndex                        INTEGER,
    --            dot11RADIUSServer                       OCTET STRING,
    --            dot11RADIUSPort                         INTEGER,
    --            dot11RADIUSSecret                       OCTET STRING
    --        }

    --        dot11RADIUSIndex                        OBJECT-TYPE
    --        SYNTAX                                  INTEGER (1..16)
    --        ACCESS                                  not-accessible
    --        STATUS                                  mandatory
    --        DESCRIPTION
    --        ""
    --        ::= { dot11RADIUSEntry 1 }

     --       dot11RADIUSServer                       OBJECT-TYPE
    --        SYNTAX                                  OCTET STRING (SIZE(0..32))
    --        ACCESS                                  read-write
    --        STATUS                                  mandatory
    --        DESCRIPTION
    --        ""
    --        ::= { dot11RADIUSEntry 2 }

     --       dot11RADIUSPort                         OBJECT-TYPE
     --       SYNTAX                                  INTEGER (0..65535)
     --       ACCESS                                  read-write
     --       STATUS                                  mandatory
     --       DESCRIPTION
     --       ""
     --       ::= { dot11RADIUSEntry 3 }

      --      dot11RADIUSSecret                       OBJECT-TYPE
      --      SYNTAX                                  OCTET STRING (SIZE(0..32))
      --      ACCESS                                  read-write
      --      STATUS                                  mandatory
      --      DESCRIPTION
      --      ""
      --      ::= { dot11RADIUSEntry 4 }

      --      dot11IpAccessControlListEntry           OBJECT-TYPE
      --      SYNTAX                                  Dot11IpAccessControlListEntry
      --      ACCESS                                  not-accessible
      --      STATUS                                  mandatory
      --      DESCRIPTION
      --      ""
       --     INDEX                                   {ifIndex, dot11IpAccessControlListIndex}
       --     ::= { dot11IpAccessControlListTable 1 }

      --      Dot11IpAccessControlListEntry
      --      ::= SEQUENCE {
      --          dot11IpAccessControlListIndex           INTEGER,
      --          dot11IpAccessControlListMacAddress      IpAddress
      --      }

      --      dot11IpAccessControlListIndex           OBJECT-TYPE
      --      SYNTAX                                  INTEGER (1..16)
      --      ACCESS                                  not-accessible
      --      STATUS                                  mandatory
      --      DESCRIPTION
      --      ""
      --      ::= { dot11IpAccessControlListEntry 1 }

      --      dot11IpAccessControlListMacAddress      OBJECT-TYPE
      --      SYNTAX                                  IpAddress
      --      ACCESS                                  read-write
      --      STATUS                                  mandatory
      --      DESCRIPTION
      --      ""
      --      ::= { dot11IpAccessControlListEntry 2 }

      --      dot11Accounting                         OBJECT  IDENTIFIER  ::= { ieee802dot11 3 }

      --      dot11AccountingTable                    OBJECT-TYPE
      --      SYNTAX                                  SEQUENCE OF Dot11AccountingEntry
      --      ACCESS                                  not-accessible
      --      STATUS                                  mandatory
      --      DESCRIPTION
       --     ""
      --      ::= { dot11Accounting 1 }

      --      dot11AccountingEntry                    OBJECT-TYPE
      --      SYNTAX                                  Dot11AccountingEntry
      --      ACCESS                                  not-accessible
      --      STATUS                                  mandatory
      --      DESCRIPTION
      --      ""
      --      INDEX                                   {ifIndex}
      --      ::= { dot11AccountingTable 1 }

      --      Dot11AccountingEntry
      --      ::= SEQUENCE {
      --          dot11AccountingStatus                   INTEGER,
      --          dot11AccountingServer                   IpAddress,
      --          dot11AccountingServerPort               INTEGER,
      --          dot11AccountingPassPhrase               OCTET STRING
      --      }

      --      dot11AccountingStatus                   OBJECT-TYPE
      --      SYNTAX                                  INTEGER {disabled(0), enabled(1)}
      --      ACCESS                                  read-write
      --      STATUS                                  mandatory
      --      DESCRIPTION
      --      ""
      --      ::= { dot11AccountingEntry 1 }

      --      dot11AccountingServer                   OBJECT-TYPE
      --      SYNTAX                                  IpAddress
      --      ACCESS                                  read-write
      --      STATUS                                  mandatory
      --      DESCRIPTION
      --      ""
      --      ::= { dot11AccountingEntry 2 }

      --      dot11AccountingServerPort               OBJECT-TYPE
      --      SYNTAX                                  INTEGER
      --      ACCESS                                  read-write
      --      STATUS                                  mandatory
      --      DESCRIPTION
      --      ""
      --      ::= { dot11AccountingEntry 3 }

      --      dot11AccountingPassPhrase               OBJECT-TYPE
      --      SYNTAX                                  OCTET STRING
      --      ACCESS                                  read-write
      --      STATUS                                  mandatory
      --      DESCRIPTION
      --      ""
      --      ::= { dot11AccountingEntry 4 }

            dot11ClientInformation                  OBJECT  IDENTIFIER  ::= { ieee802dot11 4 }

            dot11GetClientInformationTable          OBJECT-TYPE
            SYNTAX                                  SEQUENCE OF Dot11GetClientInformationEntry
            ACCESS                                  not-accessible
            STATUS                                  mandatory
            DESCRIPTION
            ""
            ::= { dot11ClientInformation 1 }

            dot11GetClientInformationEntry          OBJECT-TYPE
            SYNTAX                                  Dot11GetClientInformationEntry
            ACCESS                                  not-accessible
            STATUS                                  mandatory
            DESCRIPTION
            ""
            INDEX                                   {ifIndex}
            ::= { dot11GetClientInformationTable 1 }

            Dot11GetClientInformationEntry
            ::= SEQUENCE {
                dot11ClientInformationRefresh           INTEGER,
		dot11ClientInformationNum		INTEGER
            }

            dot11ClientInformationRefresh           OBJECT-TYPE
            SYNTAX                                  INTEGER {nothing(0), get(1)}
            ACCESS                                  read-write
            STATUS                                  mandatory
            DESCRIPTION
            ""
            ::= { dot11GetClientInformationEntry 1 }

            dot11ClientInformationNum           OBJECT-TYPE
            SYNTAX                                  INTEGER 
            ACCESS                                  read-only
            STATUS                                  mandatory
            DESCRIPTION
            ""
            ::= { dot11GetClientInformationEntry 2 }			

            dot11ClientInformationTable             OBJECT-TYPE
            SYNTAX                                  SEQUENCE OF Dot11ClientInformationEntry
            ACCESS                                  not-accessible
            STATUS                                  mandatory
            DESCRIPTION
            ""
            ::= { dot11ClientInformation 2 }

            dot11ClientInformationEntry             OBJECT-TYPE
            SYNTAX                                  Dot11ClientInformationEntry
            ACCESS                                  not-accessible
            STATUS                                  mandatory
            DESCRIPTION
            ""
            INDEX                                   {ifIndex, dot11ClientIndex}
            ::= { dot11ClientInformationTable 1 }

            Dot11ClientInformationEntry
            ::= SEQUENCE {
                dot11ClientIndex                        INTEGER,
                dot11ClientMacAddress                   MacAddress,
                dot11ClientBand                         INTEGER,
                dot11ClientAuthentication               INTEGER,
                dot11ClientRssi                         INTEGER,
                dot11ClientPsm                          INTEGER,
                dot11SSIDIndex                          OCTET STRING,
--              dot11ClientUptime                       TimeTicks,
--		dot11ActiveTime		              	TimeTicks,
--		dot11ClientIpAddress                    IpAddress,
		dot11ClientTxBytesCount			INTEGER,
		dot11ClientRxBytesCount			INTEGER,
		dot11ClientTxRate			INTEGER,
		dot11ClientSignalStrength               INTEGER	
            }

            dot11ClientIndex                        OBJECT-TYPE
            SYNTAX                                  INTEGER
            ACCESS                                  not-accessible
            STATUS                                  mandatory
            DESCRIPTION
            ""
            ::= { dot11ClientInformationEntry 1 }

            dot11ClientMacAddress                   OBJECT-TYPE
            SYNTAX                                  MacAddress
            ACCESS                                  read-only
            STATUS                                  mandatory
            DESCRIPTION
            ""
            ::= { dot11ClientInformationEntry 2 }

            dot11ClientBand                         OBJECT-TYPE
            SYNTAX                                  INTEGER { dot11b(1), dot11g(2), dot11n(3)}
            ACCESS                                  read-only
            STATUS                                  mandatory
            DESCRIPTION
            ""
            ::= { dot11ClientInformationEntry 3 }

            dot11ClientAuthentication               OBJECT-TYPE
            SYNTAX                                  INTEGER {opensystem(1),
                                                             sharedkey(2),
                                                             wpa-psk(4),
                                                             wpa-eap(5),
                                                             wpa2-psk(6),
                                                             wpa2-eap(7),
                                                             wpa2-auto-psk(8),
                                                             wpa2-auto-eap(9),
                                                             dot1x(10),
                                                             wep(11)}
            ACCESS                                  read-only
            STATUS                                  mandatory
            DESCRIPTION
            ""
            ::= { dot11ClientInformationEntry 4 }

            dot11ClientRssi                         OBJECT-TYPE
            SYNTAX                                  INTEGER
            ACCESS                                  read-only
            STATUS                                  mandatory
            DESCRIPTION
            ""
            ::= { dot11ClientInformationEntry 5 }

            dot11ClientPsm                          OBJECT-TYPE
            SYNTAX                                  INTEGER {off(0),on(1)}
            ACCESS                                  read-only
            STATUS                                  mandatory
            DESCRIPTION
            ""
            ::= { dot11ClientInformationEntry 6 }

            dot11SSIDIndex                          OBJECT-TYPE
            SYNTAX                                  OCTET STRING
            ACCESS                                  read-only
            STATUS                                  mandatory
            DESCRIPTION
            ""
            ::= { dot11ClientInformationEntry 7 }

--            dot11ClientUptime                       OBJECT-TYPE
--            SYNTAX                                  TimeTicks
--            ACCESS                                  read-only
--            STATUS                                  mandatory
--            DESCRIPTION
--            ""
--            ::= { dot11ClientInformationEntry 8 }

--            dot11ActiveTime                       OBJECT-TYPE
--            SYNTAX                                  TimeTicks
--            ACCESS                                  read-only
--            STATUS                                  mandatory
--            DESCRIPTION
--            ""
--            ::= { dot11ClientInformationEntry 9 }

--			dot11ClientIpAddress                          OBJECT-TYPE
--            SYNTAX                                  IpAddress
--            ACCESS                                  read-only
--            STATUS                                  mandatory
--            DESCRIPTION
--            ""
--            ::= { dot11ClientInformationEntry 10 }

			dot11ClientTxBytesCount	     			OBJECT-TYPE
            SYNTAX                                  INTEGER
            ACCESS                                  read-only
            STATUS                                  mandatory
            DESCRIPTION
            ""
            ::= { dot11ClientInformationEntry 11 }
            
            dot11ClientRxBytesCount	     			OBJECT-TYPE
             SYNTAX                                  INTEGER
            ACCESS                                  read-only
            STATUS                                  mandatory
            DESCRIPTION
            ""
            ::= { dot11ClientInformationEntry 12 }
	    
	    dot11ClientTxRate                           OBJECT-TYPE
            SYNTAX                                  INTEGER
            ACCESS                                  read-only
            STATUS                                  mandatory
            DESCRIPTION
            ""
            ::= { dot11ClientInformationEntry 13 }
            
            dot11ClientSignalStrength                   OBJECT-TYPE
            SYNTAX                                  INTEGER
            ACCESS                                  read-only
            STATUS                                  mandatory
            DESCRIPTION
            ""
            ::= { dot11ClientInformationEntry 14 }

            dot11WdsMonitor                  OBJECT  IDENTIFIER ::= { ieee802dot11 5 }

            dot11GetWdsTable                        OBJECT-TYPE
            SYNTAX                                  SEQUENCE OF Dot11GetWdsEntry
            ACCESS                                  not-accessible
            STATUS                                  mandatory
            DESCRIPTION
            ""
            ::= { dot11WdsMonitor 1 }

            dot11GetWdsEntry                        OBJECT-TYPE
            SYNTAX                                  Dot11GetWdsEntry
            ACCESS                                  not-accessible
            STATUS                                  mandatory
            DESCRIPTION
            ""
            INDEX                                   {ifIndex}
            ::= { dot11GetWdsTable 1 }

            Dot11GetWdsEntry
            ::= SEQUENCE
            {
                dot11WdsRefresh                         INTEGER
            }

            dot11WdsRefresh                         OBJECT-TYPE
            SYNTAX                                  INTEGER {nothing(0), get(1)}
            ACCESS                                  read-write
            STATUS                                  mandatory
            DESCRIPTION
            ""
            ::= { dot11GetWdsEntry 1 }

            dot11WdsTable                           OBJECT-TYPE
            SYNTAX                                  SEQUENCE OF Dot11WdsEntry
            ACCESS                                  not-accessible
            STATUS                                  mandatory
            DESCRIPTION
            ""
            ::= { dot11WdsMonitor 2 }

            dot11WdsEntry                           OBJECT-TYPE
            SYNTAX                                  Dot11WdsEntry
            ACCESS                                  not-accessible
            STATUS                                  mandatory
            DESCRIPTION
            ""
            INDEX                                   {ifIndex, dot11WdsIndex}
            ::= { dot11WdsTable 1 }

            Dot11WdsEntry
            ::= SEQUENCE
            {
                dot11WdsIndex                           INTEGER,
                dot11WdsMacAddress                      MacAddress,
                dot11WdsBand                            INTEGER,
                dot11WdsAuthentication                  INTEGER,
                dot11WdsRssi                            INTEGER,
           --     dot11WdsChannel                         INTEGER,
                dot11WdsSsidIndex                       OCTET STRING,
                dot11WdsConnected		                INTEGER,
                dot11WdsPsm                             INTEGER,
                dot11WdsStatus                          OCTET STRING
            }

            dot11WdsIndex                           OBJECT-TYPE
            SYNTAX                                  INTEGER
            ACCESS                                  not-accessible
            STATUS                                  mandatory
            DESCRIPTION
            ""
            ::= { dot11WdsEntry 1 }

            dot11WdsMacAddress                      OBJECT-TYPE
            SYNTAX                                  MacAddress
            ACCESS                                  read-only
            STATUS                                  mandatory
            DESCRIPTION
            ""
            ::= { dot11WdsEntry 2 }

            dot11WdsBand                            OBJECT-TYPE
            SYNTAX                                  INTEGER { dot11b(1), dot11g(2), dot11n(4)}
            ACCESS                                  read-only
            STATUS                                  mandatory
            DESCRIPTION
            ""
            ::= { dot11WdsEntry 3 }

            dot11WdsAuthentication                  OBJECT-TYPE
            SYNTAX                                  INTEGER {opensystem(1),
                                                             sharedkey(2),
                                                             wpa-enterprise(3),
                                                             wpa-personal(4),
                                                             wpa2-enterprise(6),
                                                             wpa2-personal(7),
                                                             wpa2-auto-enterprise(8),
                                                             wpa2-auto-personal(9),
                                                             wep(11)}
            ACCESS                                  read-only
            STATUS                                  mandatory
            DESCRIPTION
            ""
            ::= { dot11WdsEntry 4 }

            dot11WdsRssi                            OBJECT-TYPE
            SYNTAX                                  INTEGER
            ACCESS                                  read-only
            STATUS                                  mandatory
            DESCRIPTION
            ""
            ::= { dot11WdsEntry 5 }

    --        dot11WdsChannel                         OBJECT-TYPE
    --        SYNTAX                                  INTEGER
    --        ACCESS                                  read-only
    --        STATUS                                  mandatory
    --        DESCRIPTION
    --        ""
    --        ::= { dot11WdsEntry 6 }


            dot11WdsSsidIndex                       OBJECT-TYPE
            SYNTAX                                  OCTET STRING
            ACCESS                                  read-only
            STATUS                                  mandatory
            DESCRIPTION
            ""
            ::= { dot11WdsEntry 7 }

            dot11WdsConnected                       OBJECT-TYPE
            SYNTAX                                  INTEGER
            ACCESS                                  read-only
            STATUS                                  mandatory
            DESCRIPTION
            ""
            ::= { dot11WdsEntry 8 }

            dot11WdsStatus                       OBJECT-TYPE
            SYNTAX                                 OCTET STRING
            ACCESS                                  read-only
            STATUS                                  mandatory
            DESCRIPTION
            ""
            ::= { dot11WdsEntry 9 }

            dot11WdsPsm                         	OBJECT-TYPE
            SYNTAX                                  INTEGER  {off(0),on(1)}
            ACCESS                                  read-only
            STATUS                                  mandatory
            DESCRIPTION
            ""
            ::= { dot11WdsEntry 10 }   
            
   			dot11MacClone                    		OBJECT  IDENTIFIER ::= { ieee802dot11 6 }  
            
	        dot11MacCloneTable                      OBJECT-TYPE
            SYNTAX                                  SEQUENCE OF Dot11MacCloneEntry
            ACCESS                                  not-accessible
           	STATUS                                  mandatory
            DESCRIPTION
            ""
           ::= { dot11MacClone 1 }       
           
            dot11MacCloneEntry                      OBJECT-TYPE
            SYNTAX                                  Dot11MacCloneEntry
            ACCESS                                  not-accessible
            STATUS                                  mandatory
            DESCRIPTION
            ""
            INDEX                                   {ifIndex}
            ::= {  dot11MacCloneTable 1 }

            Dot11MacCloneEntry
            ::= SEQUENCE
            {  
                dot11MacCloneStatus                   INTEGER,
                dot11MacCloneSource                   INTEGER,
                dot11MacCloneMacAddress                 MacAddress,
                dot11MacCloneAddressRefresh           INTEGER
               
            }  
            dot11MacCloneStatus                   	OBJECT-TYPE
            SYNTAX                                  INTEGER {disabled(0), enabled(1)}
            ACCESS                                  read-write
            STATUS                                  mandatory
            DESCRIPTION
            ""
            ::= { dot11MacCloneEntry 1 }

            dot11MacCloneSource                     OBJECT-TYPE
            SYNTAX                                  INTEGER{disabled(0),auto(1), manual(2)} 
            ACCESS                                  read-write
            STATUS                                  mandatory
            DESCRIPTION
            ""
            ::= { dot11MacCloneEntry 2 } 
            
            dot11MacCloneMacAddress            		OBJECT-TYPE
            SYNTAX                                  MacAddress
            ACCESS                                  read-write
            STATUS                                  mandatory
            DESCRIPTION
           ""
            ::= { dot11MacCloneEntry 3 }

	
	    	dot11MacCloneAddressRefresh             OBJECT-TYPE
            SYNTAX                                  INTEGER{nothing(0), refresh(1)}
            ACCESS                                  read-write
            STATUS                                  mandatory
            DESCRIPTION
            ""
            ::= { dot11MacCloneEntry 4 }
             
            dot11MacCloneSurveryTable               OBJECT-TYPE
            SYNTAX                                  SEQUENCE OF Dot11MacCloneSurveryEntry
            ACCESS                                  not-accessible
            STATUS                                  mandatory
            DESCRIPTION
            ""
           ::= { dot11MacClone 2 }       
           
            dot11MacCloneSurveryEntry               OBJECT-TYPE
            SYNTAX                                  Dot11MacCloneSurveryEntry
            ACCESS                                  not-accessible
            STATUS                                  mandatory
            DESCRIPTION
            ""
            INDEX                                   { dot11MacCloneSurveryIndex}
            ::= { dot11MacCloneSurveryTable 1 }

            Dot11MacCloneSurveryEntry
            ::= SEQUENCE
            {  
            	dot11MacCloneSurveryIndex                    INTEGER,
                dot11MacCloneSurveryMacAddress               MacAddress
        
            }   
            dot11MacCloneSurveryIndex               OBJECT-TYPE
            SYNTAX                                  INTEGER
            ACCESS                                  not-accessible
            STATUS                                  mandatory   
            DESCRIPTION        
            ""
            ::= { dot11MacCloneSurveryEntry 1 }

            
            dot11MacCloneSurveryMacAddress          OBJECT-TYPE
            SYNTAX                                  MacAddress
            ACCESS                                  read-only
            STATUS                                  mandatory
            DESCRIPTION
            ""
            ::= { dot11MacCloneSurveryEntry 2 }       

            dot11ZoneDefence                       OBJECT  IDENTIFIER ::= { ieee802dot11 7 }
            dot11ZoneDefenceTable                  OBJECT-TYPE
            SYNTAX                                  SEQUENCE OF Dot11ZoneDefenceEntry
            ACCESS                                  not-accessible
            STATUS                                  mandatory
            DESCRIPTION
            ""
            ::= { dot11ZoneDefence 1 }

            dot11ZoneDefenceEntry              OBJECT-TYPE
            SYNTAX                                  Dot11ZoneDefenceEntry
            ACCESS                                  not-accessible
            STATUS                                  mandatory
            DESCRIPTION
            ""
            INDEX                                   {ifIndex}
            ::= { dot11ZoneDefenceTable 1 }

            Dot11ZoneDefenceEntry
            ::= SEQUENCE {
                dot11ZoneDefenceControl                   INTEGER,
                dot11ZoneDefenceIpAddressAdd      IpAddress,
                dot11ZoneDefenceIpAddressDelete   INTEGER
            }

            dot11ZoneDefenceControl                   OBJECT-TYPE
            SYNTAX                                  INTEGER { disabled(0), enable(1)}
            ACCESS                                  read-write
            STATUS                                  mandatory
            DESCRIPTION
            ""
            ::= { dot11ZoneDefenceEntry 1 }

            dot11ZoneDefenceIpAddressAdd     	    OBJECT-TYPE
            SYNTAX                                  IpAddress
            ACCESS                                  read-write
            STATUS                                  mandatory
            DESCRIPTION
            ""
            ::= { dot11ZoneDefenceEntry 2 }

            dot11ZoneDefenceIpAddressDelete	     OBJECT-TYPE
            SYNTAX                                  INTEGER
            ACCESS                                  read-write
            STATUS                                  mandatory
            DESCRIPTION
            ""
            ::= { dot11ZoneDefenceEntry 3 }

            dot11ZoneDefenceIpAddressListTable          OBJECT-TYPE
            SYNTAX                                  SEQUENCE OF Dot11ZoneDefenceIpAddressListEntry
            ACCESS                                  not-accessible
            STATUS                                  mandatory
            DESCRIPTION
            ""
            ::= {  dot11ZoneDefence 2 }

            dot11ZoneDefenceIpAddressListEntry          OBJECT-TYPE
            SYNTAX                                  Dot11ZoneDefenceIpAddressListEntry
            ACCESS                                  not-accessible
            STATUS                                  mandatory
            DESCRIPTION
            ""
            INDEX                                   {ifIndex, dot11ZoneDefenceIpAddressListIndex}
            ::= { dot11ZoneDefenceIpAddressListTable 1 }

            Dot11ZoneDefenceIpAddressListEntry
            ::= SEQUENCE {
                dot11ZoneDefenceIpAddressListIndex          INTEGER,
                dot11ZoneDefenceIpAddressList     IpAddress
            }

           dot11ZoneDefenceIpAddressListIndex          OBJECT-TYPE
            SYNTAX                                  INTEGER (1..16)
            ACCESS                                  not-accessible
            STATUS                                  mandatory
            DESCRIPTION
            ""
            ::= { dot11ZoneDefenceIpAddressListEntry 1 }


            dot11ZoneDefenceIpAddressList     OBJECT-TYPE
            SYNTAX                                  IpAddress
            ACCESS                                  read-only
            STATUS                                  mandatory
            DESCRIPTION
            ""
            ::= { dot11ZoneDefenceIpAddressListEntry 2 }

      --      ieee802dot16                            OBJECT  IDENTIFIER ::= { wirelesslan 4 }

      --      dot16Parameters                         OBJECT  IDENTIFIER ::= { ieee802dot16 1 }

      --      wan                                     OBJECT  IDENTIFIER ::= { interface 2 }
      
      --      wanIfSetting                            OBJECT  IDENTIFIER ::= { wan 1 }

      --      wiredWan                                OBJECT  IDENTIFIER ::= { wan 2 }

     --       wirelessWan                             OBJECT  IDENTIFIER ::= { wan 3 }
      
            advance                                 OBJECT  IDENTIFIER ::= { dap2360B 3 }

            dhcpServer                              OBJECT  IDENTIFIER ::= { advance 1 }

            dhcpServerControl                       OBJECT-TYPE
            SYNTAX                                  INTEGER {disabled(0), enabled(1)}
            ACCESS                                  read-write
            STATUS                                  mandatory
            DESCRIPTION
            ""
            ::= { dhcpServer 1 }

            dhcpServerDynamicParameter              OBJECT IDENTIFIER ::= { dhcpServer 2 }

            dhcpServerDynamicControl                OBJECT-TYPE
            SYNTAX                                  INTEGER {disabled(0), enabled(1)}
            ACCESS                                  read-write
            STATUS                                  mandatory
            DESCRIPTION
            ""
            ::= { dhcpServerDynamicParameter 1 }

            dhcpServerDomainNameStatus				OBJECT-TYPE
            SYNTAX                                  INTEGER {both(0),dynamic(1), static(2)}
            ACCESS                                  read-only
            STATUS                                  mandatory
            DESCRIPTION
            ""
            ::= { dhcpServerDynamicParameter 3 }  


            dhcpServerDynamicTable                  OBJECT-TYPE
            SYNTAX                                  SEQUENCE OF DhcpServerDynamicEntry
            ACCESS                                  not-accessible
            STATUS                                  mandatory
            DESCRIPTION
            ""
            ::= { dhcpServerDynamicParameter 2 }

            dhcpServerDynamicEntry                  OBJECT-TYPE
            SYNTAX                                  DhcpServerDynamicEntry
            ACCESS                                  not-accessible
            STATUS                                  mandatory
            DESCRIPTION
            ""
            INDEX                                   {dynamicIndex}
            ::= { dhcpServerDynamicTable 1 }

            DhcpServerDynamicEntry
            ::= SEQUENCE {
                dynamicIndex                            INTEGER,
           --     dynamicPoolStatus                       INTEGER,
                dynamicIpPoolStart                      IpAddress,
                dynamicIpPoolEnd                        IpAddress,
          --      dynamicIpPoolRange                      INTEGER,
                dynamicMask                             IpAddress,
                dynamicGateway                          IpAddress,
                dynamicWins                             IpAddress,
                dynamicDns                              IpAddress,
                dynamicDns                              IpAddress,
                dynamicDomainName                       OCTET STRING,
                dynamicLeaseTime                        INTEGER
            }

            dynamicIndex                            OBJECT-TYPE
            SYNTAX                                  INTEGER
            ACCESS                                  not-accessible
            STATUS                                  mandatory
            DESCRIPTION
            ""
            ::= { dhcpServerDynamicEntry 1 }

      --      dynamicPoolStatus                       OBJECT-TYPE
      --      SYNTAX                                  INTEGER {disabled(0), enabled(1)}
      --      ACCESS                                  read-write
      --      STATUS                                  mandatory
      --      DESCRIPTION
      --      ""
      --      ::= { dhcpServerDynamicEntry 2 }

            dynamicIpPoolStart                      OBJECT-TYPE
            SYNTAX                                  IpAddress
            ACCESS                                  read-write
            STATUS                                  mandatory
            DESCRIPTION
            ""
            ::= { dhcpServerDynamicEntry 3 }

            dynamicIpPoolEnd                        OBJECT-TYPE
            SYNTAX                                  IpAddress
            ACCESS                                  read-write
            STATUS                                  mandatory
            DESCRIPTION
            ""
            ::= { dhcpServerDynamicEntry 4 }

      --      dynamicIpPoolRange                      OBJECT-TYPE
      --      SYNTAX                                  INTEGER (0..255)
      --      ACCESS                                  read-write
      --      STATUS                                  mandatory
      --      DESCRIPTION
      --      ""
      --      ::= { dhcpServerDynamicEntry 5 }

            dynamicMask                             OBJECT-TYPE
            SYNTAX                                  IpAddress
            ACCESS                                  read-write
            STATUS                                  mandatory
            DESCRIPTION
            ""
            ::= { dhcpServerDynamicEntry 6 }

            dynamicGateway                          OBJECT-TYPE
            SYNTAX                                  IpAddress
            ACCESS                                  read-write
            STATUS                                  mandatory
            DESCRIPTION
            ""
            ::= { dhcpServerDynamicEntry 7 }

            dynamicWins                             OBJECT-TYPE
            SYNTAX                                  IpAddress
            ACCESS                                  read-write
            STATUS                                  mandatory
            DESCRIPTION
            ""
            ::= { dhcpServerDynamicEntry 8 }

            dynamicDns                              OBJECT-TYPE
            SYNTAX                                  IpAddress
            ACCESS                                  read-write
            STATUS                                  mandatory
            DESCRIPTION
            ""
            ::= { dhcpServerDynamicEntry 9 }

            dynamicDomainName                       OBJECT-TYPE
            SYNTAX                                  OCTET STRING (SIZE(0..64))
            ACCESS                                  read-write
            STATUS                                  mandatory
            DESCRIPTION
            ""
            ::= { dhcpServerDynamicEntry 10 }

            dynamicLeaseTime                        OBJECT-TYPE
            SYNTAX                                  INTEGER (60..31536000)
            ACCESS                                  read-write
            STATUS                                  mandatory
            DESCRIPTION
            ""
            ::= { dhcpServerDynamicEntry 11 }

            dhcpServerStaticParameter               OBJECT IDENTIFIER ::= { dhcpServer 3 }

            dhcpServerStaticControl                 OBJECT-TYPE
            SYNTAX                                  INTEGER {disabled(0), enabled(1)}
            ACCESS                                  read-write
            STATUS                                  mandatory
            DESCRIPTION
            ""
            ::= { dhcpServerStaticParameter 1 }

            dhcpServerStaticDelete                 	OBJECT-TYPE
            SYNTAX                                  INTEGER (1..25)
            ACCESS                                  read-write
            STATUS                                  mandatory
            DESCRIPTION
            ""
            ::= { dhcpServerStaticParameter 3 }

            dhcpServerStaticTable                   OBJECT-TYPE
            SYNTAX                                  SEQUENCE OF DhcpServerStaticEntry
            ACCESS                                  not-accessible
            STATUS                                  mandatory
            DESCRIPTION
            ""
            ::= { dhcpServerStaticParameter 2 }

            dhcpServerStaticEntry                   OBJECT-TYPE
            SYNTAX                                  DhcpServerStaticEntry
            ACCESS                                  not-accessible
            STATUS                                  mandatory
            DESCRIPTION
            ""
            INDEX                                   {staticIndex}
            ::= { dhcpServerStaticTable 1 }

            DhcpServerStaticEntry
            ::= SEQUENCE {
                staticIndex                             INTEGER,
                staticEntryStatus                       INTEGER,
                staticHostName                          OCTET STRING,
                staticIP                                IpAddress,
                staticMac                               MacAddress,
                staticMask                              IpAddress,
                staticGateway                           IpAddress,
                staticDns                               IpAddress,
                staticWins                              IpAddress,
                staticDomainName                        OCTET STRING
            }

            staticIndex                             OBJECT-TYPE
            SYNTAX                                  INTEGER
            ACCESS                                  not-accessible
            STATUS                                  mandatory
            DESCRIPTION
            ""
            ::= { dhcpServerStaticEntry 1 }

            staticEntryStatus                       OBJECT-TYPE
            SYNTAX                                  INTEGER {disabled(0), enabled(1)}
            ACCESS                                  read-write
            STATUS                                  mandatory
            DESCRIPTION
            ""
            ::= { dhcpServerStaticEntry 2 }

            staticHostName                          OBJECT-TYPE
            SYNTAX                                  OCTET STRING (SIZE(0..64))
            ACCESS                                  read-write
            STATUS                                  mandatory
            DESCRIPTION
            ""
            ::= { dhcpServerStaticEntry 3 }

            staticIP                                OBJECT-TYPE
            SYNTAX                                  IpAddress
            ACCESS                                  read-write
            STATUS                                  mandatory
            DESCRIPTION
            ""
            ::= { dhcpServerStaticEntry 4 }

            staticMac                               OBJECT-TYPE
            SYNTAX                                  MacAddress
            ACCESS                                  read-write
            STATUS                                  mandatory
            DESCRIPTION
            ""
            ::= { dhcpServerStaticEntry 5 }

            staticMask                              OBJECT-TYPE
            SYNTAX                                  IpAddress
            ACCESS                                  read-write
            STATUS                                  mandatory
            DESCRIPTION
            ""
            ::= { dhcpServerStaticEntry 6 }

            staticGateway                           OBJECT-TYPE
            SYNTAX                                  IpAddress
            ACCESS                                  read-write
            STATUS                                  mandatory
            DESCRIPTION
            ""
            ::= { dhcpServerStaticEntry 7 }

            staticDns                               OBJECT-TYPE
            SYNTAX                                  IpAddress
            ACCESS                                  read-write
            STATUS                                  mandatory
            DESCRIPTION
            ""
            ::= { dhcpServerStaticEntry 8 }

            staticWins                              OBJECT-TYPE
            SYNTAX                                  IpAddress
            ACCESS                                  read-write
            STATUS                                  mandatory
            DESCRIPTION
            ""
            ::= { dhcpServerStaticEntry 9 }

            staticDomainName                        OBJECT-TYPE
            SYNTAX                                  OCTET STRING(SIZE(0..64))
            ACCESS                                  read-write
            STATUS                                  mandatory
            DESCRIPTION
            ""
            ::= { dhcpServerStaticEntry 10 }

            dhcpServerCurrentList                   OBJECT  IDENTIFIER ::= { dhcpServer 4 }

            refreshCurrentDynamicList               OBJECT-TYPE
            SYNTAX                                  INTEGER {nothing(0), refresh(1)}
            ACCESS                                  read-write
            STATUS                                  mandatory
            DESCRIPTION
            ""
            ::= { dhcpServerCurrentList 1 }

            currentDynamicTable                     OBJECT-TYPE
            SYNTAX                                  SEQUENCE OF CurrentDynamicEntry
            ACCESS                                  not-accessible
            STATUS                                  mandatory
            DESCRIPTION
            ""
            ::= { dhcpServerCurrentList 2 }

            currentDynamicEntry                     OBJECT-TYPE
            SYNTAX                                  CurrentDynamicEntry
            ACCESS                                  not-accessible
            STATUS                                  mandatory
            DESCRIPTION
            ""
            INDEX                                   {currentDynamicIndex}
            ::= { currentDynamicTable 1 }

            CurrentDynamicEntry
            ::= SEQUENCE {
                currentDynamicIndex                     INTEGER,
                currentDynamicHostName                  OCTET STRING,
                currentDynamicMacAddress                MacAddress,
                currentDynamicAssignedIP                IpAddress,
                currentDynamicLease                     TimeTicks
            }

            currentDynamicIndex                         OBJECT-TYPE
            SYNTAX                                      INTEGER
            ACCESS                                      not-accessible
            STATUS                                      mandatory
            DESCRIPTION
            ""
            ::= { currentDynamicEntry 1 }

            currentDynamicHostName                  OBJECT-TYPE
            SYNTAX                                  OCTET STRING (SIZE(0..64))
            ACCESS                                  read-write
            STATUS                                  mandatory
            DESCRIPTION
            ""
            ::= { currentDynamicEntry 2 }

            currentDynamicMacAddress                OBJECT-TYPE
            SYNTAX                                  MacAddress
            ACCESS                                  read-only
            STATUS                                  mandatory
            DESCRIPTION
            ""
            ::= { currentDynamicEntry 3 }

            currentDynamicAssignedIP                OBJECT-TYPE
            SYNTAX                                  IpAddress
            ACCESS                                  read-only
            STATUS                                  mandatory
            DESCRIPTION
            ""
            ::= { currentDynamicEntry 4 }

            currentDynamicLease                     OBJECT-TYPE
            SYNTAX                                  TimeTicks
            ACCESS                                  read-only
            STATUS                                  mandatory
            DESCRIPTION
            ""
            ::= { currentDynamicEntry 5 }

            refreshCurrentStaticList                OBJECT-TYPE
            SYNTAX                                  INTEGER {nothing(0), refresh(1)}
            ACCESS                                  read-write
            STATUS                                  mandatory
            DESCRIPTION
            ""
            ::= { dhcpServerCurrentList 3 }

            currentStaticTable                      OBJECT-TYPE
            SYNTAX                                  SEQUENCE OF CurrentStaticEntry
            ACCESS                                  not-accessible
            STATUS                                  mandatory
            DESCRIPTION
            ""
            ::= { dhcpServerCurrentList 4 }

            currentStaticEntry                      OBJECT-TYPE
            SYNTAX                                  CurrentStaticEntry
            ACCESS                                  not-accessible
            STATUS                                  mandatory
            DESCRIPTION
            ""
            INDEX                                   {currentStaticIndex}
            ::= { currentStaticTable 1 }

            CurrentStaticEntry
            ::= SEQUENCE {
                currentStaticIndex                      INTEGER,
                currentStaticHostName                   OCTET STRING,
                currentStaticMacAddress                 MacAddress,
                currentStaticAssignedIP                 IpAddress
            }

            currentStaticIndex                      OBJECT-TYPE
            SYNTAX                                  INTEGER
            ACCESS                                  not-accessible
            STATUS                                  mandatory
            DESCRIPTION
            ""
            ::= { currentStaticEntry 1 }

            currentStaticHostName                   OBJECT-TYPE
            SYNTAX                                  OCTET STRING (SIZE(0..64))
            ACCESS                                  read-only
            STATUS                                  mandatory
            DESCRIPTION
            ""
            ::= { currentStaticEntry 2 }

            currentStaticMacAddress                 OBJECT-TYPE
            SYNTAX                                  MacAddress
            ACCESS                                  read-only
            STATUS                                  mandatory
            DESCRIPTION
            ""
            ::= { currentStaticEntry 3 }

            currentStaticAssignedIP                 OBJECT-TYPE
            SYNTAX                                  IpAddress
            ACCESS                                  read-only
            STATUS                                  mandatory
            DESCRIPTION
            ""
            ::= { currentStaticEntry 4 }

            ieee802dot11Grouping                      OBJECT  IDENTIFIER ::= { advance 2 }

            dot11GroupingTable                      OBJECT-TYPE
            SYNTAX                                  SEQUENCE OF Dot11GroupingEntry
            ACCESS                                  not-accessible
            STATUS                                  mandatory
            DESCRIPTION
            ""
            ::= { ieee802dot11Grouping 1 }

            dot11GroupingEntry                      OBJECT-TYPE
            SYNTAX                                  Dot11GroupingEntry
            ACCESS                                  not-accessible
            STATUS                                  mandatory
            DESCRIPTION
            ""
            INDEX                                   {ifIndex}
            ::= { dot11GroupingTable 1 }

            Dot11GroupingEntry
            ::= SEQUENCE {
                dot11LoadBalance                       INTEGER,
                dot11UserLimit                         INTEGER,
                dot11LinkIntegrate                     INTEGER
         --       dot11EthernetLinkStatus                 INTEGER,
--                dot11NetworkUtilization                 INTEGER
            }

            dot11LoadBalance                        OBJECT-TYPE
            SYNTAX                                  INTEGER {disabled(0), enabled(1)}
            ACCESS                                  read-write
            STATUS                                  mandatory
            DESCRIPTION
            ""
            ::= { dot11GroupingEntry 1 }

            dot11UserLimit                          OBJECT-TYPE
            SYNTAX                                  INTEGER (0..64)
            ACCESS                                  read-write
            STATUS                                  mandatory
            DESCRIPTION
            ""
            ::= { dot11GroupingEntry 2 }

            dot11LinkIntegrate                      OBJECT-TYPE
            SYNTAX                                  INTEGER {disabled(0), enabled(1)}
            ACCESS                                  read-write
            STATUS                                  mandatory
            DESCRIPTION
            ""
            ::= { dot11GroupingEntry 3 }

   --         dot11EthernetLinkStatus                 OBJECT-TYPE
   --         SYNTAX                                  INTEGER {linkDown(0), linkUp(1)}
   --         ACCESS                                  read-only
   --         STATUS                                  mandatory
    --        DESCRIPTION
   --         ""
    --        ::= { dot11GroupingEntry 4 }

--            dot11NetworkUtilization                 OBJECT-TYPE
--           SYNTAX                                  INTEGER { zero(0),
--                                                             tenPercent(1),
--                                                             twentyPercent(2),
--                                                              thirtyPercent(3),
--                                                             fourtyPercent(4),
--                                                              fiftyPercent(5),
--                                                              sixtyPercent(6),
--                                                              seventyPercent(7),
--                                                              eightyPercent(8),
--                                                              nintyPercent(9),
--                                                              hundryPercent(10) }
--            ACCESS                                  read-write
--            STATUS                                  mandatory
--            DESCRIPTION
--            ""
--            ::= { dot11GroupingEntry 5 }

            ieee802dot11MultiSsid                   OBJECT  IDENTIFIER ::= { advance 3 }


            dot11MssidStateTable                    OBJECT-TYPE
            SYNTAX                                  SEQUENCE OF Dot11MssidStateEntry
            ACCESS not-accessible
            STATUS mandatory
            DESCRIPTION
            ""
            ::= { ieee802dot11MultiSsid 1 }

            dot11MssidStateEntry                    OBJECT-TYPE
            SYNTAX                                  Dot11MssidStateEntry
            ACCESS                                  not-accessible
            STATUS                                  mandatory
            DESCRIPTION
            ""
            INDEX                                   {ifIndex}
            ::= { dot11MssidStateTable 1 }

            Dot11MssidStateEntry
            ::= SEQUENCE {
                dot11MssidState                         INTEGER,
                dot11MssidPriorityState                 INTEGER
            }

            dot11MssidState                         OBJECT-TYPE
            SYNTAX                                  INTEGER {disabled(0), enabled(1)}
            ACCESS                                  read-write
            STATUS                                  mandatory
            DESCRIPTION
            ""
            ::= { dot11MssidStateEntry 1 }

            dot11MssidPriorityState                 OBJECT-TYPE
            SYNTAX                                  INTEGER {disabled(0), enabled(1)}
            ACCESS                                  read-write
            STATUS                                  mandatory
            DESCRIPTION
            ""
            ::= { dot11MssidStateEntry 2 }

--            dot11VlanTable                          OBJECT-TYPE
--            SYNTAX                                  SEQUENCE OF Dot11VlanEntry
--            ACCESS                                  not-accessible
--            STATUS                                  mandatory
--            DESCRIPTION
--            ""
--            ::= { ieee802dot11MultiSsid 2 }

--            dot11VlanEntry                          OBJECT-TYPE
--            SYNTAX                                  Dot11VlanEntry
--            ACCESS                                  not-accessible
--            STATUS                                  mandatory
--            DESCRIPTION
--            ""
--            INDEX                                   {ifIndex}
--            ::= { dot11VlanTable 1 }

--            Dot11VlanEntry
--            ::= SEQUENCE {
--                dot11VlanState                          INTEGER
--            }

--            dot11VlanState                          OBJECT-TYPE
--            SYNTAX                                  INTEGER {disabled(0), enabled(1)}
--            ACCESS                                  read-write
--            STATUS                                  mandatory
--            DESCRIPTION
--            ""
--            ::= { dot11VlanEntry 1 }

            dot11MssidTable                         OBJECT-TYPE
            SYNTAX                                  SEQUENCE OF Dot11MssidEntry
            ACCESS                                  not-accessible
            STATUS                                  mandatory
            DESCRIPTION
            ""
            ::= { ieee802dot11MultiSsid 3 }

            dot11MssidEntry                         OBJECT-TYPE
            SYNTAX                                  Dot11MssidEntry
            ACCESS                                  not-accessible
            STATUS                                  mandatory
            DESCRIPTION
            ""
            INDEX                                   {ifIndex, dot11MssidIndex}
            ::= { dot11MssidTable 1 }

            Dot11MssidEntry
            ::= SEQUENCE {
                dot11MssidIndex                         INTEGER,
                dot11MssIndividualState                 INTEGER,
                dot11MssidSsid                          OCTET STRING,
                dot11MssidSuppress                      INTEGER,
                dot11MssidAuthentication                INTEGER,
                dot11MssidEncryption                    INTEGER,
                dot11MssidWepKeyIndex                   INTEGER,
                dot11MssidWepKey                        OCTET STRING,
--                dot11MssidVlanTagID                     INTEGER,
                dot11MssidCipherType                    INTEGER,
                dot11MssidPassPhrase                    OCTET STRING,
                dot11MssidKeyType                       INTEGER,
            --    dot11MssidEthernetSelect                INTEGER,
                dot11MssidWmm                           INTEGER,
                dot11MssidGroupKeyUpdateInterval        INTEGER,
                dot11MssidPriority                      INTEGER,
                dot11MssidAutoRekeyControl                   INTEGER,
                dot11MssidAutoRekeyStartWeek                 INTEGER,
                dot11MssidAutoRekeyStartTime                 OCTET STRING,
                dot11MssidAutoRekeyTimeInterval              INTEGER,
                dot11MssidAutoRekeyPassPhrase                OCTET STRING
            }

            dot11MssidIndex                         OBJECT-TYPE
            SYNTAX                                  INTEGER
            ACCESS                                  not-accessible
            STATUS                                  mandatory
            DESCRIPTION
            ""
            ::= { dot11MssidEntry 1 }

            dot11MssIndividualState                 OBJECT-TYPE
            SYNTAX                                  INTEGER {disabled(0), enabled(1)}
            ACCESS                                  read-write
            STATUS                                  mandatory
            DESCRIPTION
            ""
            ::= { dot11MssidEntry 2 }

            dot11MssidSsid                          OBJECT-TYPE
            SYNTAX                                  OCTET STRING (SIZE(0..32))
            ACCESS                                  read-write
            STATUS                                  mandatory
            DESCRIPTION
            ""
            ::= { dot11MssidEntry 3 }

            dot11MssidSuppress                      OBJECT-TYPE
            SYNTAX                                  INTEGER {disabled(0), enabled(1)}
            ACCESS                                  read-write
            STATUS                                  mandatory
            DESCRIPTION
            ""
            ::= { dot11MssidEntry 4 }

            dot11MssidAuthentication                OBJECT-TYPE
            SYNTAX                                  INTEGER {opensystem(1),
                                                             sharedkey(2),
                                                             opensystem-sharedkey(3),
                                                             wpa-psk(4),
                                                             wpa-eap(5),
                                                             wpa2-psk(6),
                                                             wpa2-eap(7),
                                                             wpa2-auto-psk(8),
                                                             wpa2-auto-eap(9),
                                                             dot1x(10)}
            ACCESS                                  read-write
            STATUS                                  mandatory
            DESCRIPTION
            ""
            ::= { dot11MssidEntry 5 }

            dot11MssidEncryption                    OBJECT-TYPE
            SYNTAX                                  INTEGER {disabled(0), enabled(1)}
            ACCESS                                  read-write
            STATUS                                  mandatory
            DESCRIPTION
            ""
            ::= { dot11MssidEntry 6 }

            dot11MssidWepKeyIndex                   OBJECT-TYPE
            SYNTAX                                  INTEGER {first(1),
                                                             second(2),
                                                             third(3),
                                                             fourth(4)}
            ACCESS                                  read-write
            STATUS                                  mandatory
            DESCRIPTION
            ""
            ::= { dot11MssidEntry 7 }

            dot11MssidWepKey                        OBJECT-TYPE
            SYNTAX                                  OCTET STRING
            ACCESS                                  read-write
            STATUS                                  mandatory
            DESCRIPTION
            ""
            ::= { dot11MssidEntry 8 }

--            dot11MssidVlanTagID                     OBJECT-TYPE
--            SYNTAX                                  INTEGER (1..4095)
--            ACCESS                                  read-write
--            STATUS                                  mandatory
--            DESCRIPTION
--            ""
--            ::= { dot11MssidEntry 9 }

            dot11MssidCipherType                    OBJECT-TYPE
            SYNTAX                                  INTEGER {auto(1), aes(2), tkip(3), wep(4)}
            ACCESS                                  read-write
            STATUS                                  mandatory
            DESCRIPTION
            ""
            ::= { dot11MssidEntry 10 }

            dot11MssidPassPhrase                    OBJECT-TYPE
            SYNTAX                                  OCTET STRING (SIZE(8..63))
            ACCESS                                  read-write
            STATUS                                  mandatory
            DESCRIPTION
            ""
            ::= { dot11MssidEntry 11 }

            dot11MssidKeyType                       OBJECT-TYPE
            SYNTAX                                  INTEGER {ascii(1), hex(2)}
            ACCESS                                  read-write
            STATUS                                  mandatory
            DESCRIPTION
            ""
            ::= { dot11MssidEntry 12 }

      --      dot11MssidEthernetSelect                OBJECT-TYPE
      --      SYNTAX                                  INTEGER {ethernet1(1),ethernet2(2)}
      --      ACCESS                                  read-write
      --      STATUS                                  mandatory
      --      DESCRIPTION
      --      ""
      --      ::= { dot11MssidEntry 13 }


            dot11MssidWmm                           OBJECT-TYPE
            SYNTAX                                  INTEGER {disabled(0), enabled(1)}
            ACCESS                                  read-write
            STATUS                                  mandatory
            DESCRIPTION
            ""
            ::= { dot11MssidEntry 14 }

            dot11MssidGroupKeyUpdateInterval        OBJECT-TYPE
            SYNTAX                                  INTEGER (300..9999999)
            ACCESS                                  read-write
            STATUS                                  mandatory
            DESCRIPTION
            ""
            ::= { dot11MssidEntry 15 }

           dot11MssidPriority						   	OBJECT-TYPE
            SYNTAX                                  	INTEGER(0..7)
            ACCESS                                  	read-write
            STATUS                                  	mandatory
            DESCRIPTION
            ""
            ::= { dot11MssidEntry 16 }  
            
            dot11MssidAutoRekeyControl     				OBJECT-TYPE
            SYNTAX                                  	INTEGER{disable(0), enable(1)}
            ACCESS                                  	read-write
            STATUS                                  	mandatory
            DESCRIPTION
            "disable( Manual ) , enable(Periodrical Key Change )"
            ::= { dot11MssidEntry 17 }  
            
            dot11MssidAutoRekeyStartWeek     			OBJECT-TYPE
            SYNTAX                                  	INTEGER{sun(0),
                                                            mon(1),
                                                            tue(2),
                                                            wed(3),
                                                            thu(4),
                                                            fri(5),
                                                            sat(6)}
            ACCESS                                  	read-write
            STATUS                                  	mandatory
            DESCRIPTION
            ""
            ::= { dot11MssidEntry 18 }   
            
            dot11MssidAutoRekeyStartTime   				OBJECT-TYPE
            SYNTAX                                  	OCTET STRING
            ACCESS                                  	read-write
            STATUS                                  	mandatory
            DESCRIPTION
            " Please follow this format: 'xx:xx'
              For example: 23:45 "
            ::= { dot11MssidEntry 19 }

            
            dot11MssidAutoRekeyTimeInterval     		OBJECT-TYPE
            SYNTAX                                  	INTEGER(1..168)
            ACCESS                                  	read-write
            STATUS                                  	mandatory
            DESCRIPTION
            ""            
            ::= { dot11MssidEntry 20 } 
            
            dot11MssidAutoRekeyPassPhrase     			OBJECT-TYPE
            SYNTAX                                  	OCTET STRING
            ACCESS                                  	read-only
            STATUS                                  	mandatory
            DESCRIPTION
            ""            
            ::= { dot11MssidEntry 21 }


            dot11MssidRADIUSTable                   OBJECT-TYPE
            SYNTAX                                  SEQUENCE OF Dot11MssidRADIUSEntry
            ACCESS                                  not-accessible
            STATUS                                  mandatory
            DESCRIPTION
            ""
            ::= { ieee802dot11MultiSsid 4 }

            dot11MssidRADIUSEntry                   OBJECT-TYPE
            SYNTAX                                  Dot11MssidRADIUSEntry
            ACCESS                                  not-accessible
            STATUS                                  mandatory
            DESCRIPTION
            ""
            INDEX                                   { dot11MssidRADIUSIndex ,dot11MssidIndex}
            ::= { dot11MssidRADIUSTable 1 }

            Dot11MssidRADIUSEntry
            ::= SEQUENCE {
                dot11MssidRADIUSIndex                   INTEGER,
                dot11MssidRADIUSServer                  IpAddress,
                dot11MssidRADIUSPort                    INTEGER,
                dot11MssidRADIUSSecret                  OCTET STRING,
--              	dot11MssidRadiusSource                       INTEGER,
		dot11MssidRadiusKeyUpdateInterval		INTEGER
            }

            dot11MssidRADIUSIndex                   OBJECT-TYPE
            SYNTAX                                  INTEGER
            ACCESS                                  not-accessible
            STATUS                                  mandatory
            DESCRIPTION
            ""
            ::= { dot11MssidRADIUSEntry 1 }

            dot11MssidRADIUSServer                  OBJECT-TYPE
            SYNTAX                                  IpAddress
            ACCESS                                  read-write
            STATUS                                  mandatory
            DESCRIPTION
            ""
            ::= { dot11MssidRADIUSEntry 2 }

            dot11MssidRADIUSPort                    OBJECT-TYPE
            SYNTAX                                  INTEGER (0..65535)
            ACCESS                                  read-write
            STATUS                                  mandatory
            DESCRIPTION
            ""
            ::= { dot11MssidRADIUSEntry 3 }

            dot11MssidRADIUSSecret                  OBJECT-TYPE
            SYNTAX                                  OCTET STRING (SIZE(0..32))
            ACCESS                                  read-write
            STATUS                                  mandatory
            DESCRIPTION
            ""
            ::= { dot11MssidRADIUSEntry 4 }

--            dot11MssidRadiusSource   			OBJECT-TYPE
--            SYNTAX                                  	INTEGER{remote(1), local(2)}
--            ACCESS                                  	read-write
--            STATUS                                  	mandatory
--            DESCRIPTION
--            ""
--            ::= { dot11MssidRADIUSEntry 5 }

            dot11MssidRadiusKeyUpdateInterval   	OBJECT-TYPE
            SYNTAX                                  	INTEGER
            ACCESS                                  	read-write
            STATUS                                  	mandatory
            DESCRIPTION
            ""
            ::= { dot11MssidRADIUSEntry 6 }

--            dot11MssidAccountingTable               OBJECT-TYPE
--            SYNTAX                                  SEQUENCE OF Dot11MssidAccountingEntry
--            ACCESS                                  not-accessible
--            STATUS                                  mandatory
--            DESCRIPTION
--            ""
--            ::= { ieee802dot11MultiSsid 5 }

--            dot11MssidAccountingEntry               OBJECT-TYPE
--            SYNTAX                                  Dot11MssidAccountingEntry
--            ACCESS                                  not-accessible
--            STATUS                                  mandatory
--            DESCRIPTION
--            ""
--            INDEX                                   {dot11MssidAccountingIndex,dot11MssidIndex}
--            ::= { dot11MssidAccountingTable 1 }

--            Dot11MssidAccountingEntry
--            ::= SEQUENCE {
--                dot11MssidAccountingIndex               INTEGER,
--                dot11MssidAccountingStatus              INTEGER,
--                dot11MssidAccountingServer              IpAddress,
--                dot11MssidAccountingServerPort          INTEGER,
--                dot11MssidAccountingPassPhrase          OCTET STRING
--            }

--            dot11MssidAccountingIndex               OBJECT-TYPE
--            SYNTAX                                  INTEGER
--            ACCESS                                  not-accessible
--            STATUS                                  mandatory
--            DESCRIPTION
--            ""
--            ::= { dot11MssidAccountingEntry 1 }

--            dot11MssidAccountingStatus              OBJECT-TYPE
--            SYNTAX                                  INTEGER {disabled(0), enabled(1)}
--            ACCESS                                  read-write
--            STATUS                                  mandatory
--            DESCRIPTION
--            ""
--            ::= { dot11MssidAccountingEntry 2 }

--            dot11MssidAccountingServer              OBJECT-TYPE
--            SYNTAX                                  IpAddress
--            ACCESS                                  read-write
--            STATUS                                  mandatory
--            DESCRIPTION
--            ""
--            ::= { dot11MssidAccountingEntry 3 }

--            dot11MssidAccountingServerPort          OBJECT-TYPE
--            SYNTAX                                  INTEGER
--            ACCESS                                  read-write
--            STATUS                                  mandatory
--            DESCRIPTION
--            ""
--            ::= { dot11MssidAccountingEntry 4 }

--            dot11MssidAccountingPassPhrase          OBJECT-TYPE
--            SYNTAX                                  OCTET STRING
--            ACCESS                                  read-write
--            STATUS                                  mandatory
--            DESCRIPTION
--            ""
--            ::= { dot11MssidAccountingEntry 5 }

            ieee802dot11RogueApDetection            OBJECT  IDENTIFIER ::= { advance 4 }

     --       dot11RogueApBssType                     OBJECT-TYPE
     --       SYNTAX                                  INTEGER {infrastructure(1), independent(2), any(3)}
     --       ACCESS                                  read-write
     --       STATUS                                  mandatory
     --       DESCRIPTION
     --       ""
     --       ::= { ieee802dot11RogueApDetection 1 }

     --       dot11RogueApBandType                    OBJECT-TYPE
     --       SYNTAX                                  INTEGER
     --       ACCESS                                  read-write
     --       STATUS                                  mandatory
     --       DESCRIPTION
     --       ""
     --       ::= { ieee802dot11RogueApDetection 2 }

     --       dot11RogueApSecurityType                OBJECT-TYPE
     --       SYNTAX                                  INTEGER
     --       ACCESS                                  read-write
     --       STATUS                                  mandatory
     --       DESCRIPTION
     --       ""
     --       ::= { ieee802dot11RogueApDetection 3 }

            dot11RogueApSurvey                      OBJECT  IDENTIFIER ::= { ieee802dot11RogueApDetection 4 }

            dot11RogueApSurveyRefresh               OBJECT-TYPE
            SYNTAX                                  INTEGER {nothing(0), refresh(1)}
            ACCESS                                  read-write
            STATUS                                  mandatory
            DESCRIPTION
            ""
            ::= { dot11RogueApSurvey 1 }

      --      dot11RogueApAddtoApList                 OBJECT-TYPE
      --      SYNTAX                                  INTEGER (1..128)
      --      ACCESS                                  read-write
      --      STATUS                                  mandatory
      --      DESCRIPTION
      --      ""
      --      ::= { dot11RogueApSurvey 2 }

      --      dot11RogueApDelete                     OBJECT-TYPE
      --      SYNTAX                                  INTEGER (1..128)
      --      ACCESS                                  read-write
      --      STATUS                                  mandatory
      --      DESCRIPTION
      --      ""
      --      ::= { dot11RogueApSurvey 3 }
	    
	    
	    dot11RogueApAddtoValid                  OBJECT-TYPE
            SYNTAX                                  INTEGER (1..256)
            ACCESS                                  read-write
            STATUS                                  mandatory
            DESCRIPTION
            ""
            ::= { dot11RogueApSurvey 5 }
            
            dot11RogueApAddtoNeighbor               OBJECT-TYPE
            SYNTAX                                  INTEGER (1..256)
            ACCESS                                  read-write
            STATUS                                  mandatory
            DESCRIPTION
            ""
            ::= { dot11RogueApSurvey 6 }

            dot11RogueApAddtoRouge                  OBJECT-TYPE
            SYNTAX                                  INTEGER (1..256)
            ACCESS                                  read-write
            STATUS                                  mandatory
            DESCRIPTION
            ""
            ::= { dot11RogueApSurvey 7 }
            
            dot11RogueApAddtoNew                    OBJECT-TYPE
            SYNTAX                                  INTEGER (1..256)
            ACCESS                                  read-write
            STATUS                                  mandatory
            DESCRIPTION
            ""
            ::= { dot11RogueApSurvey 8 } 
            
            dot11RogueApAllNewNodesAsValid          OBJECT-TYPE
            SYNTAX                                  INTEGER {disable(0), enable(1)}
            ACCESS                                  read-write
            STATUS                                  mandatory
            DESCRIPTION
            ""
            ::= { dot11RogueApSurvey 9 }  
            
            dot11RogueApAllNewNodesAsRogue       OBJECT-TYPE
            SYNTAX                                  	INTEGER {disable(0), enable(1)}
            ACCESS                                  	read-write
            STATUS                                  	mandatory
            DESCRIPTION
            ""
            ::= { dot11RogueApSurvey 10 }


            dot11RogueApSurveyTable                 OBJECT-TYPE
            SYNTAX                                  SEQUENCE OF Dot11RogueApSurveyEntry
            ACCESS                                  not-accessible
            STATUS                                  mandatory
            DESCRIPTION
            ""
            ::= { dot11RogueApSurvey 4 }

            dot11RogueApSurveyEntry                 OBJECT-TYPE
            SYNTAX                                  Dot11RogueApSurveyEntry
            ACCESS                                  not-accessible
            STATUS                                  mandatory
            DESCRIPTION
            ""
            INDEX                                   { dot11RogueApSurveyIndex }
            ::= { dot11RogueApSurveyTable 1 }

            Dot11RogueApSurveyEntry
            ::= SEQUENCE {
                dot11RogueApSurveyIndex                 INTEGER,
          --      dot11RogueApSurveyBssType               OCTET STRING,
                dot11RogueApSurveyChannel               INTEGER,
                dot11RogueApSurveyRssi                  INTEGER,
                dot11RogueApSurveyBssid                 MacAddress,
         --       dot11RogueApSurveyAuthentication        INTEGER,
          --      dot11RogueApSurveyEncryption            OCTET STRING,
                dot11RogueApSurveyMode                  INTEGER,
                dot11RogueApSurveySsid                  OCTET STRING,
                dot11RogueApSurveyLastseen              OCTET STRING,
                dot11RogueApSurveyType                	INTEGER,
                dot11RogueApSurveyStatus                INTEGER
            }

            dot11RogueApSurveyIndex                 OBJECT-TYPE
            SYNTAX                                  INTEGER
            ACCESS                                  not-accessible
            STATUS                                  mandatory
            DESCRIPTION
            ""
            ::= { dot11RogueApSurveyEntry 1 }

    --        dot11RogueApSurveyBssType               OBJECT-TYPE
    --        SYNTAX                                  OCTET STRING
    --        ACCESS                                  read-only
    --        STATUS                                  mandatory
    --        DESCRIPTION
    --        ""
    --        ::= { dot11RogueApSurveyEntry 2 }

            dot11RogueApSurveyChannel               OBJECT-TYPE
            SYNTAX                                  INTEGER
            ACCESS                                  read-only
            STATUS                                  mandatory
            DESCRIPTION
            ""
            ::= { dot11RogueApSurveyEntry 3 }

            dot11RogueApSurveyRssi                  OBJECT-TYPE
            SYNTAX                                  INTEGER
            ACCESS                                  read-only
            STATUS                                  mandatory
            DESCRIPTION
            ""
            ::= { dot11RogueApSurveyEntry 4 }

            dot11RogueApSurveyBssid                 OBJECT-TYPE
            SYNTAX                                  MacAddress
            ACCESS                                  read-only
            STATUS                                   mandatory
            DESCRIPTION
            ""
            ::= { dot11RogueApSurveyEntry 5 }

    --        dot11RogueApSurveyAuthentication        OBJECT-TYPE
    --        SYNTAX                                  INTEGER {off(1),
    --                                                         wep(2),
    --                                                         wpa-eap(3),
    --                                                         wpa-psk(4),
    --                                                         wpa2-eap(5),
    --                                                         wpa2-psk(6),
    --                                                         wpa-auto-eap(7),
    --                                                         wpa-auto-psk(8),
    --                                                         dot1x(9)}
    --        ACCESS                                  read-only
    --        STATUS                                  mandatory
    --        DESCRIPTION
    --        ""
    --        ::= { dot11RogueApSurveyEntry 6 }

    --        dot11RogueApSurveyEncryption            OBJECT-TYPE
    --        SYNTAX                                  OCTET STRING
    --        ACCESS                                  read-only
    --        STATUS                                  mandatory
    --        DESCRIPTION
    --        ""
    --        ::= { dot11RogueApSurveyEntry 7 }

            dot11RogueApSurveyMode                  OBJECT-TYPE
            SYNTAX                                  INTEGER {dot11g(1), dot11n(2), dot11a(3), dot11b(4)}
            ACCESS                                  read-only
            STATUS                                  mandatory
            DESCRIPTION
            ""
            ::= { dot11RogueApSurveyEntry 8 }

            dot11RogueApSurveySsid                  OBJECT-TYPE
            SYNTAX                                  OCTET STRING (SIZE(0..32))
            ACCESS                                  read-only
            STATUS                                  mandatory
            DESCRIPTION
            ""
            ::= { dot11RogueApSurveyEntry 9 }

            
            dot11RogueApSurveyLastseen              OBJECT-TYPE
            SYNTAX                                  OCTET STRING
            ACCESS                                  read-only
            STATUS                                  mandatory
            DESCRIPTION
            ""
            ::= { dot11RogueApSurveyEntry 10 } 
                 
             dot11RogueApSurveyType      			OBJECT-TYPE
            SYNTAX                                  INTEGER {new(1), valid(2),neighborhood(3),rogue(4)}
            ACCESS                                  read-only
            STATUS                                  mandatory
            DESCRIPTION
            ""                                        
            ::= { dot11RogueApSurveyEntry 11 }  

              dot11RogueApSurveyStatus              OBJECT-TYPE
            SYNTAX                                  INTEGER {up(2), down(1)}
            ACCESS                                  read-only
            STATUS                                  mandatory
            DESCRIPTION
            ""
            ::= { dot11RogueApSurveyEntry 12 }  


            dot11RogueApListRecord                  OBJECT  IDENTIFIER ::= { ieee802dot11RogueApDetection 5 }

            dot11RogueApDeleteFromRecord            OBJECT-TYPE
            SYNTAX                                  INTEGER (1..30)
            ACCESS                                  read-write
            STATUS                                  mandatory
            DESCRIPTION
            ""
            ::= { dot11RogueApListRecord 1 }

            dot11RogueApListRecordTable             OBJECT-TYPE
            SYNTAX                                  SEQUENCE OF Dot11RogueApListRecordEntry
            ACCESS                                  not-accessible
            STATUS                                  mandatory
            DESCRIPTION
            ""
            ::= { dot11RogueApListRecord 2 }

            dot11RogueApListRecordEntry             OBJECT-TYPE
            SYNTAX                                  Dot11RogueApListRecordEntry
            ACCESS                                  not-accessible
            STATUS                                  mandatory
            DESCRIPTION
            ""
            INDEX                                   { dot11RogueApListRecordIndex }
            ::= { dot11RogueApListRecordTable 1 }

            Dot11RogueApListRecordEntry
            ::= SEQUENCE {
                dot11RogueApListRecordIndex             INTEGER,
           --     dot11RogueApListRecordBssType          OCTET STRING,
                dot11RogueApListRecordChannel           INTEGER,
                dot11RogueApListRecordRssi              INTEGER,
                dot11RogueApListRecordBssid             MacAddress,
           --     dot11RogueApListRecordAuthentication    INTEGER,
           --     dot11RogueApListRecordEncryption        OCTET STRING,
                dot11RogueApListRecordMode              INTEGER,
                dot11RogueApListRecordSsid              OCTET STRING,
                dot11RogueApListRecordLastseen          OCTET STRING,
                dot11RogueApListRecordType              INTEGER,
                dot11RogueApListRecordStatus			INTEGER
            }

            dot11RogueApListRecordIndex             OBJECT-TYPE
            SYNTAX                                  INTEGER
            ACCESS                                  not-accessible
            STATUS                                  mandatory
            DESCRIPTION
            ""
            ::= { dot11RogueApListRecordEntry 1 }

     --       dot11RogueApListRecordBssType           OBJECT-TYPE
     --       SYNTAX                                  OCTET STRING
     --       ACCESS                                  read-only
     --       STATUS                                  mandatory
     --       DESCRIPTION
     --       ""
     --       ::= { dot11RogueApListRecordEntry 2 }

            dot11RogueApListRecordChannel           OBJECT-TYPE
            SYNTAX                                  INTEGER
            ACCESS                                  read-only
            STATUS                                  mandatory
            DESCRIPTION
            ""
            ::= { dot11RogueApListRecordEntry 3 }

            dot11RogueApListRecordRssi              OBJECT-TYPE
            SYNTAX                                  INTEGER
            ACCESS                                  read-only
            STATUS                                  mandatory
            DESCRIPTION
            ""
            ::= { dot11RogueApListRecordEntry 4 }

            dot11RogueApListRecordBssid             OBJECT-TYPE
            SYNTAX                                  MacAddress
            ACCESS                                  read-only
            STATUS                                  mandatory
            DESCRIPTION
            ""
            ::= { dot11RogueApListRecordEntry 5 }

    --        dot11RogueApListRecordAuthentication    OBJECT-TYPE
     --       SYNTAX                                  INTEGER {off(1),
    --                                                         wep(2),
    --                                                         wpa-eap(3),
    --                                                         wpa-psk(4),
    --                                                         wpa2-eap(5),
    --                                                         wpa2-psk(6),
    --                                                         wpa-auto-eap(7),
     --                                                        wpa-auto-psk(8),
     --                                                        dot1x(9)}
     --       ACCESS                                  read-only
     --       STATUS                                  mandatory
     --       DESCRIPTION
     --       ""
     --       ::= { dot11RogueApListRecordEntry 6 }

    --        dot11RogueApListRecordEncryption        OBJECT-TYPE
    --        SYNTAX                                  OCTET STRING
    --        ACCESS                                  read-only
    --        STATUS                                  mandatory
    --        DESCRIPTION
    --        ""
    --        ::= { dot11RogueApListRecordEntry 7 }

            dot11RogueApListRecordMode              OBJECT-TYPE
            SYNTAX                                  INTEGER {dot11a(0), dot11b(2), dot11g(3), dot11n(4)}
            ACCESS                                  read-only
            STATUS                                  mandatory
            DESCRIPTION
            ""
            ::= { dot11RogueApListRecordEntry 8 }

            dot11RogueApListRecordSsid              OBJECT-TYPE
            SYNTAX                                  OCTET STRING (SIZE(0..32))
            ACCESS                                  read-only
            STATUS                                  mandatory
            DESCRIPTION
            ""
            ::= { dot11RogueApListRecordEntry 9 }

            dot11RogueApListRecordLastseen          OBJECT-TYPE
            SYNTAX                                  OCTET STRING
            ACCESS                                  read-only
            STATUS                                  mandatory
            DESCRIPTION
            ""
            ::= { dot11RogueApListRecordEntry 10 } 
            
            dot11RogueApListRecordType           	OBJECT-TYPE
            SYNTAX                                  INTEGER {new(1), valid(2),neighborhood(3),rogue(4)}
            ACCESS                                  read-only
            STATUS                                  mandatory
            DESCRIPTION
            ""
            ::= { dot11RogueApListRecordEntry 11 }  
            
            dot11RogueApListRecordStatus            OBJECT-TYPE
            SYNTAX                                  INTEGER {up(2), down(1)}
            ACCESS                                  read-only
            STATUS                                  mandatory
            DESCRIPTION
            ""
            ::= { dot11RogueApListRecordEntry 12 } 


   --         ieee802dot11DataRateControl                      OBJECT  IDENTIFIER ::= { advance 5 }

  --          dot11DataRateControlTable               OBJECT-TYPE
  --          SYNTAX                                  SEQUENCE OF Dot11DataRateControlEntry
  --          ACCESS                                  not-accessible
  --          STATUS                                  mandatory
  --          DESCRIPTION
   --         ""
   --         ::= { ieee802dot11DataRateControl 1 }

   --         dot11DataRateControlEntry               OBJECT-TYPE
   --         SYNTAX                                  Dot11DataRateControlEntry
   --         ACCESS                                  not-accessible
   --         STATUS                                  mandatory
   --         DESCRIPTION
   --         ""
   --         INDEX                                   {ifIndex}
   --         ::= { dot11DataRateControlTable 1 }

   --         Dot11DataRateControlEntry
   --         ::= SEQUENCE {
   --             dot11DataRateControl                    INTEGER,
   --             dot11DataRateSetDefault                 INTEGER
   --         }

  --          dot11DataRateControl                    OBJECT-TYPE
  --          SYNTAX                                  INTEGER {disabled(0), enabled(1)}
  --          ACCESS                                  read-write
  --          STATUS                                  mandatory
  --          DESCRIPTION
  --          ""
  --          ::= { dot11DataRateControlEntry 1 }

  --          dot11DataRateSetDefault                    OBJECT-TYPE
  --          SYNTAX                                  INTEGER {nothing(0), set(1)}
  --          ACCESS                                  read-write
  --          STATUS                                  mandatory
  --          DESCRIPTION
  --          ""
  --          ::= { dot11DataRateControlEntry 2 }

  --          dot11DataRateTable                      OBJECT-TYPE
  --          SYNTAX                                  SEQUENCE OF Ieee802dot11DataRateEntry
  --          ACCESS                                  not-accessible
  --          STATUS                                  mandatory
  --          DESCRIPTION
   --         ""
   --         ::= { ieee802dot11DataRateControl 2 }

   --         ieee802dot11DataRateEntry               OBJECT-TYPE
   --         SYNTAX                                  Ieee802dot11DataRateEntry
   --         ACCESS                                  not-accessible
   --         STATUS                                  mandatory
   --         DESCRIPTION
   --         ""
   --         INDEX                                   {ifIndex}
   --         ::= { dot11DataRateTable 1 }

   --         Ieee802dot11DataRateEntry
   --         ::= SEQUENCE {
    --            dot11DataRate1Mb                      INTEGER,
    --            dot11DataRate2Mb                      INTEGER,
    --            dot11DataRate5dot5Mb                  INTEGER,
    --            dot11DataRate6Mb                      INTEGER,
    --            dot11DataRate9Mb                      INTEGER,
    --            dot11DataRate11Mb                     INTEGER,
    --            dot11DataRate12Mb                     INTEGER,
    --            dot11DataRate18Mb                     INTEGER,
    --            dot11DataRate24Mb                     INTEGER,
    --            dot11DataRate36Mb                     INTEGER,
    --            dot11DataRate48Mb                     INTEGER,
    --            dot11DataRate54Mb                     INTEGER
     --       }

    --        dot11DataRate1Mb                        OBJECT-TYPE
    --        SYNTAX                                  INTEGER {disabled(0), enabled(1),basic(3)}
    --        ACCESS                                  read-write
    --        STATUS                                  mandatory
    --        DESCRIPTION
    --        ""
    --        ::= { ieee802dot11DataRateEntry 1 }

    --        dot11DataRate2Mb                        OBJECT-TYPE
    --        SYNTAX                                  INTEGER {disabled(0), enabled(1),basic(3)}
    --        ACCESS                                  read-write
    --        STATUS                                  mandatory
    --        DESCRIPTION
    --        ""
    --        ::= { ieee802dot11DataRateEntry 2 }

    --        dot11DataRate5dot5Mb                    OBJECT-TYPE
    --        SYNTAX                                  INTEGER {disabled(0), enabled(1),basic(3)}
    --        ACCESS                                  read-write
    --        STATUS                                  mandatory
    --        DESCRIPTION
    --        ""
    --        ::= { ieee802dot11DataRateEntry 3 }

    --        dot11DataRate6Mb                        OBJECT-TYPE
    --        SYNTAX                                  INTEGER {disabled(0), enabled(1),basic(3)}
    --        ACCESS                                  read-write
    --        STATUS                                  mandatory
   --         DESCRIPTION
    --        ""
    --        ::= { ieee802dot11DataRateEntry 4 }

    --        dot11DataRate9Mb                        OBJECT-TYPE
    --        SYNTAX                                  INTEGER {disabled(0), enabled(1),basic(3)}
    --        ACCESS                                  read-write
    --        STATUS                                  mandatory
    --        DESCRIPTION
    --        ""
    --        ::= { ieee802dot11DataRateEntry 5 }

    --        dot11DataRate11Mb                       OBJECT-TYPE
    --       SYNTAX                                  INTEGER {disabled(0), enabled(1),basic(3)}
     --       ACCESS                                  read-write
    --        STATUS                                  mandatory
    --        DESCRIPTION
    --        ""
    --        ::= { ieee802dot11DataRateEntry 6 }

    --        dot11DataRate12Mb                       OBJECT-TYPE
    --        SYNTAX                                  INTEGER {disabled(0), enabled(1),basic(3)}
    --        ACCESS                                  read-write
    --        STATUS                                  mandatory
    --        DESCRIPTION
    --        ""
    --        ::= { ieee802dot11DataRateEntry 7 }

    --        dot11DataRate18Mb                       OBJECT-TYPE
    --        SYNTAX                                  INTEGER {disabled(0), enabled(1),basic(3)}
    --        ACCESS                                  read-write
    --        STATUS                                  mandatory
    --        DESCRIPTION
    --        ""
    --        ::= { ieee802dot11DataRateEntry 8 }

    --        dot11DataRate24Mb                       OBJECT-TYPE
    --        SYNTAX                                  INTEGER {disabled(0), enabled(1),basic(3)}
    --        ACCESS                                  read-write
    --        STATUS                                  mandatory
    --        DESCRIPTION
    --        ""
    --        ::= { ieee802dot11DataRateEntry 9 }

    --        dot11DataRate36Mb                       OBJECT-TYPE
    --        SYNTAX                                  INTEGER {disabled(0), enabled(1),basic(3)}
    --        ACCESS                                  read-write
    --        STATUS                                  mandatory
    --        DESCRIPTION
    --        ""
    --        ::= { ieee802dot11DataRateEntry 10 }

    --        dot11DataRate48Mb                       OBJECT-TYPE
    --        SYNTAX                                  INTEGER {disabled(0), enabled(1),basic(3)}
    --        ACCESS                                  read-write
    --        STATUS                                  mandatory
    --        DESCRIPTION
    --        ""
    --        ::= { ieee802dot11DataRateEntry 11 }

    --        dot11DataRate54Mb                       OBJECT-TYPE
    --        SYNTAX                                  INTEGER {disabled(0), enabled(1),basic(3)}
    --        ACCESS                                  read-write
    --        STATUS                                  mandatory
    --        DESCRIPTION
     --       ""
     --       ::= { ieee802dot11DataRateEntry 12 }

              ieee802dot11VLAN            			OBJECT  IDENTIFIER ::= { advance 6 }

            dot11VLANParameter                      OBJECT  IDENTIFIER ::= { ieee802dot11VLAN 1 }

            dot11VlanStatus               			OBJECT-TYPE
            SYNTAX                                  INTEGER {disable(0), enable(1)}
            ACCESS                                  read-write
            STATUS                                  mandatory
            DESCRIPTION
            ""
            ::= { dot11VLANParameter 1 }

            dot11VlanMode                    		OBJECT-TYPE
            SYNTAX                                  INTEGER {static(0), dynamic(1)}
            ACCESS                                  read-only
            STATUS                                  mandatory
            DESCRIPTION
            ""
            ::= { dot11VLANParameter 2 } 
            
            dot11GroupVlanListTable                 OBJECT-TYPE
            SYNTAX                                  SEQUENCE OF Dot11GroupVlanListEntry
            ACCESS                                  not-accessible
            STATUS                                  mandatory
            DESCRIPTION
            ""
            ::= { dot11VLANParameter  3 }  
            
            dot11GroupVlanListEntry                 OBJECT-TYPE
            SYNTAX                                  Dot11GroupVlanListEntry
            ACCESS                                  not-accessible
            STATUS                                  mandatory
            DESCRIPTION
            ""
            INDEX                                   { dot11GroupVlanListIndex }
            ::= { dot11GroupVlanListTable  1 }

            Dot11GroupVlanListEntry
            ::= SEQUENCE {     
            	dot11GroupVlanListIndex            INTEGER,
                dot11GroupVlanListVid              INTEGER,
                dot11GroupVlanListName             OCTET STRING,
                dot11GroupVlanListMgmt             INTEGER,
                dot11GroupVlanListLan              INTEGER,
                dot11GroupVlanListPrimary          INTEGER,
                dot11GroupVlanListMssid1           INTEGER,
                dot11GroupVlanListMssid2           INTEGER,
                dot11GroupVlanListMssid3           INTEGER,
                dot11GroupVlanListMssid4           INTEGER,
				dot11GroupVlanListMssid5           INTEGER,
				dot11GroupVlanListMssid6           INTEGER,
				dot11GroupVlanListMssid7           INTEGER,
				dot11GroupVlanListWds1             INTEGER,
				dot11GroupVlanListWds2             INTEGER,
				dot11GroupVlanListWds3             INTEGER,
				dot11GroupVlanListWds4             INTEGER,
				dot11GroupVlanListWds5             INTEGER,
				dot11GroupVlanListWds6             INTEGER,
				dot11GroupVlanListWds7             INTEGER,
				dot11GroupVlanListWds8             INTEGER,
                dot11VlanListSurveydelete		   INTEGER
            }
            dot11GroupVlanListIndex             	OBJECT-TYPE
            SYNTAX                                  INTEGER
            ACCESS                                  not-accessible
            STATUS                                  mandatory
            DESCRIPTION
            ""
            ::= { dot11GroupVlanListEntry 1 }

            dot11GroupVlanListVid           		OBJECT-TYPE
            SYNTAX                                  INTEGER
            ACCESS                                  read-write
            STATUS                                  mandatory
            DESCRIPTION
            ""
            ::= { dot11GroupVlanListEntry 2 }
            
            dot11GroupVlanListName           		OBJECT-TYPE
            SYNTAX                                  OCTET STRING(SIZE(0..64))
            ACCESS                                  read-write
            STATUS                                  mandatory
            DESCRIPTION
            ""
            ::= { dot11GroupVlanListEntry 3 }
            
            dot11GroupVlanListMgmt           		OBJECT-TYPE
            SYNTAX                                  INTEGER {none(0), tag(1),untag(2)}
            ACCESS                                  read-write
            STATUS                                  mandatory
            DESCRIPTION
            ""
            ::= { dot11GroupVlanListEntry 4 }
            
            dot11GroupVlanListLan                  	OBJECT-TYPE
            SYNTAX                                  INTEGER{none(0), tag(1),untag(2)}
            ACCESS                                  read-write
            STATUS                                  mandatory
            DESCRIPTION
            ""
            ::= { dot11GroupVlanListEntry 5 }   
            
               
            dot11GroupVlanListPrimary              	OBJECT-TYPE
            SYNTAX                                  INTEGER{none(0), tag(1),untag(2)}
            ACCESS                                  read-write
            STATUS                                  mandatory
            DESCRIPTION
            ""
            ::= { dot11GroupVlanListEntry 6 }       
               
            dot11GroupVlanListMssid1              	OBJECT-TYPE
            SYNTAX                                  INTEGER {none(0), tag(1),untag(2)}
            ACCESS                                  read-write
            STATUS                                  mandatory
            DESCRIPTION
            ""
            ::= { dot11GroupVlanListEntry 7 }    
            
            dot11GroupVlanListMssid2               	OBJECT-TYPE
            SYNTAX                                  INTEGER {none(0), tag(1),untag(2)}
            ACCESS                                  read-write
            STATUS                                  mandatory
            DESCRIPTION
            ""
            ::= { dot11GroupVlanListEntry 8 }  
            
            dot11GroupVlanListMssid3            	OBJECT-TYPE
            SYNTAX                                  INTEGER {none(0), tag(1),untag(2)}
            ACCESS                                  read-write
            STATUS                                  mandatory
            DESCRIPTION
            ""
            ::= { dot11GroupVlanListEntry 9 } 
            
            dot11GroupVlanListMssid4               	OBJECT-TYPE
            SYNTAX                                  INTEGER {none(0), tag(1),untag(2)}
            ACCESS                                  read-write
            STATUS                                  mandatory
            DESCRIPTION
            ""
            ::= { dot11GroupVlanListEntry 10 } 
            
            dot11GroupVlanListMssid5               	OBJECT-TYPE
            SYNTAX                                  INTEGER {none(0), tag(1),untag(2)}
            ACCESS                                  read-write
            STATUS                                  mandatory
            DESCRIPTION
            ""
            ::= { dot11GroupVlanListEntry 11 } 
            
            dot11GroupVlanListMssid6              	OBJECT-TYPE
            SYNTAX                                  INTEGER {none(0), tag(1),untag(2)}
            ACCESS                                  read-write
            STATUS                                  mandatory
            DESCRIPTION
            ""
            ::= { dot11GroupVlanListEntry 12 } 
            
            dot11GroupVlanListMssid7              	OBJECT-TYPE
            SYNTAX                                  INTEGER {none(0), tag(1),untag(2)}
            ACCESS                                  read-write
            STATUS                                  mandatory
            DESCRIPTION
            ""
            ::= { dot11GroupVlanListEntry 13 } 
            
            dot11GroupVlanListWds1                  OBJECT-TYPE
            SYNTAX                                  INTEGER {none(0), tag(1),untag(2)}
            ACCESS                                  read-write
            STATUS                                  mandatory
            DESCRIPTION
            ""
            ::= { dot11GroupVlanListEntry 14 }   
            
            dot11GroupVlanListWds2                  OBJECT-TYPE
            SYNTAX                                  INTEGER{none(0), tag(1),untag(2)}
            ACCESS                                  read-write
            STATUS                                  mandatory
            DESCRIPTION
            ""
            ::= { dot11GroupVlanListEntry 15 }
            
            dot11GroupVlanListWds3                  OBJECT-TYPE
            SYNTAX                                  INTEGER {none(0), tag(1),untag(2)}
            ACCESS                                  read-write
            STATUS                                  mandatory
            DESCRIPTION
            ""
            ::= { dot11GroupVlanListEntry 16 }
            
            dot11GroupVlanListWds4                  OBJECT-TYPE
            SYNTAX                                  INTEGER {none(0), tag(1),untag(2)}
            ACCESS                                  read-write
            STATUS                                  mandatory
            DESCRIPTION
            ""
            ::= { dot11GroupVlanListEntry 17 }
            
            dot11GroupVlanListWds5                  OBJECT-TYPE
            SYNTAX                                  INTEGER {none(0), tag(1),untag(2)}
            ACCESS                                  read-write
            STATUS                                  mandatory
            DESCRIPTION
            ""
            ::= { dot11GroupVlanListEntry 18 }
            
            dot11GroupVlanListWds6                  OBJECT-TYPE
            SYNTAX                                  INTEGER {none(0), tag(1),untag(2)}
            ACCESS                                  read-write
            STATUS                                  mandatory
            DESCRIPTION
            ""
            ::= { dot11GroupVlanListEntry 19 }
            
            dot11GroupVlanListWds7                  OBJECT-TYPE
            SYNTAX                                  INTEGER{none(0), tag(1),untag(2)}
            ACCESS                                  read-write
            STATUS                                  mandatory
            DESCRIPTION
            ""
            ::= { dot11GroupVlanListEntry 20 }
            
            dot11GroupVlanListWds8                  OBJECT-TYPE
            SYNTAX                                  INTEGER {none(0), tag(1),untag(2)}
            ACCESS                                  read-write
            STATUS                                  mandatory
            DESCRIPTION
            ""
            ::= { dot11GroupVlanListEntry 21 }
                  
            dot11VlanListSurveydelete           	OBJECT-TYPE
            SYNTAX                                  INTEGER {nothing(0), delete(1)}
            ACCESS                                  read-write
            STATUS                                  mandatory
            DESCRIPTION
            ""
            ::= { dot11GroupVlanListEntry 22 }  
                       
           dot11PvidSettingRecord                   OBJECT  IDENTIFIER ::= { ieee802dot11VLAN 2 }

            dot11PvidAutoAssignStatus				OBJECT-TYPE
            SYNTAX                                  INTEGER {disable(0), enable(1)}
            ACCESS                                  read-write
            STATUS                                  mandatory
            DESCRIPTION
            ""
            ::= { dot11PvidSettingRecord 1 }

            
            dot11PvidSettingTable                 	OBJECT-TYPE
            SYNTAX                                  SEQUENCE OF Dot11PvidSettingEntry
            ACCESS                                  not-accessible
            STATUS                                  mandatory
            DESCRIPTION
            ""
            ::= { dot11PvidSettingRecord 2 }   
  
            
            
            dot11PvidSettingEntry             		OBJECT-TYPE
            SYNTAX                                  Dot11PvidSettingEntry
            ACCESS                                  not-accessible
            STATUS                                  mandatory
            DESCRIPTION
            ""
            INDEX                                   { dot11PvidSettingIndex}
            ::= { dot11PvidSettingTable 1 }

            Dot11PvidSettingEntry
            ::= SEQUENCE {
                dot11PvidSettingIndex            INTEGER,
                dot11PvidSettingMgmt             INTEGER,
                dot11PvidSettingLan              INTEGER,
                dot11PvidSettingPrimary          INTEGER,
                dot11PvidSettingMssid1           INTEGER,
                dot11PvidSettingMssid2           INTEGER,
                dot11PvidSettingMssid3           INTEGER,
                dot11PvidSettingMssid4           INTEGER,
		dot11PvidSettingMssid5           INTEGER,
		dot11PvidSettingMssid6           INTEGER,
		dot11PvidSettingMssid7           INTEGER,
		dot11PvidSettingWds1             INTEGER,
		dot11PvidSettingWds2             INTEGER,
		dot11PvidSettingWds3             INTEGER,
		dot11PvidSettingWds4             INTEGER,
		dot11PvidSettingWds5             INTEGER,
		dot11PvidSettingWds6             INTEGER,
		dot11PvidSettingWds7             INTEGER,
		dot11PvidSettingWds8             INTEGER
            }  
            
            dot11PvidSettingIndex             		OBJECT-TYPE
            SYNTAX                                  INTEGER
            ACCESS                                  not-accessible
            STATUS                                  mandatory
            DESCRIPTION
            ""
            ::= { dot11PvidSettingEntry 1 }

            dot11PvidSettingMgmt                  	OBJECT-TYPE
            SYNTAX                                  INTEGER(1..4094)
            ACCESS                                  read-write
            STATUS                                  mandatory
            DESCRIPTION
            ""
            ::= { dot11PvidSettingEntry 2 } 
            
            dot11PvidSettingLan                   	OBJECT-TYPE
            SYNTAX                                  INTEGER(1..4094)
            ACCESS                                  read-write
            STATUS                                  mandatory
            DESCRIPTION
            ""
            ::= { dot11PvidSettingEntry 3 }
            
            dot11PvidSettingPrimary                	OBJECT-TYPE
            SYNTAX                                  INTEGER(1..4094)
            ACCESS                                  read-write
            STATUS                                  mandatory
            DESCRIPTION
            ""
            ::= { dot11PvidSettingEntry 4 }
           
            dot11PvidSettingMssid1                	OBJECT-TYPE
            SYNTAX                                  INTEGER(1..4094)
            ACCESS                                  read-write
            STATUS                                  mandatory
            DESCRIPTION
            ""
            ::= { dot11PvidSettingEntry 5 }
            
            dot11PvidSettingMssid2                 	OBJECT-TYPE
            SYNTAX                                  INTEGER(1..4094)
            ACCESS                                  read-write
            STATUS                                  mandatory
            DESCRIPTION
            ""
            ::= { dot11PvidSettingEntry 6 }
            
            dot11PvidSettingMssid3                 	OBJECT-TYPE
            SYNTAX                                  INTEGER(1..4094)
            ACCESS                                  read-write
            STATUS                                  mandatory
            DESCRIPTION
            ""
            ::= { dot11PvidSettingEntry 7 }
            
            dot11PvidSettingMssid4                 	OBJECT-TYPE
            SYNTAX                                  INTEGER(1..4094)
            ACCESS                                  read-write
            STATUS                                  mandatory
            DESCRIPTION
            ""
            ::= { dot11PvidSettingEntry 8 }
            
            dot11PvidSettingMssid5                 	OBJECT-TYPE
            SYNTAX                                  INTEGER(1..4094)
            ACCESS                                  read-write
            STATUS                                  mandatory
            DESCRIPTION
            ""
            ::= { dot11PvidSettingEntry 9 }
            
            dot11PvidSettingMssid6                  	OBJECT-TYPE
            SYNTAX                                  INTEGER(1..4094)
            ACCESS                                  read-write
            STATUS                                  mandatory
            DESCRIPTION
            ""
            ::= { dot11PvidSettingEntry 10 }
            
            dot11PvidSettingMssid7                  	OBJECT-TYPE
            SYNTAX                                  INTEGER(1..4094)
            ACCESS                                  read-write
            STATUS                                  mandatory
            DESCRIPTION
            ""
            ::= { dot11PvidSettingEntry 11 }
            
            dot11PvidSettingWds1                  	OBJECT-TYPE
            SYNTAX                                  INTEGER(1..4094)
            ACCESS                                  read-write
            STATUS                                  mandatory
            DESCRIPTION
            ""
            ::= { dot11PvidSettingEntry 12 }
            
            dot11PvidSettingWds2                  	OBJECT-TYPE
            SYNTAX                                  INTEGER(1..4094)
            ACCESS                                  read-write
            STATUS                                  mandatory
            DESCRIPTION
            ""
            ::= { dot11PvidSettingEntry 13 }
            
            dot11PvidSettingWds3                  	OBJECT-TYPE
            SYNTAX                                  INTEGER(1..4094)
            ACCESS                                  read-write
            STATUS                                  mandatory
            DESCRIPTION
            ""
            ::= { dot11PvidSettingEntry 14 }
            
            dot11PvidSettingWds4                  	OBJECT-TYPE
            SYNTAX                                  INTEGER(1..4094)
            ACCESS                                  read-write
            STATUS                                  mandatory
            DESCRIPTION
            ""
            ::= { dot11PvidSettingEntry 15 }
            
            dot11PvidSettingWds5                  	OBJECT-TYPE
            SYNTAX                                  INTEGER(1..4094)
            ACCESS                                  read-write
            STATUS                                  mandatory
            DESCRIPTION
            ""
            ::= { dot11PvidSettingEntry 16 }
            
            dot11PvidSettingWds6                  	OBJECT-TYPE
            SYNTAX                                  INTEGER(1..4094)
            ACCESS                                  read-write
            STATUS                                  mandatory
            DESCRIPTION
            ""
            ::= { dot11PvidSettingEntry 17 }
            
            dot11PvidSettingWds7                  	OBJECT-TYPE
            SYNTAX                                  INTEGER(1..4094)
            ACCESS                                  read-write
            STATUS                                  mandatory
            DESCRIPTION
            ""
            ::= { dot11PvidSettingEntry 18 }
            
            dot11PvidSettingWds8                  	OBJECT-TYPE
            SYNTAX                                  INTEGER(1..4094)
            ACCESS                                  read-write
            STATUS                                  mandatory
            DESCRIPTION
            ""
            ::= { dot11PvidSettingEntry 19 }
            
          	dot11PortListRecord                   OBJECT  IDENTIFIER ::= { ieee802dot11VLAN 3 }

 			dot11PortListRefresh               		OBJECT-TYPE
            SYNTAX                                  INTEGER {nothing(0), refresh(1)}
            ACCESS                                  read-write
            STATUS                                  mandatory
            DESCRIPTION
            ""
            ::= { dot11PortListRecord 1 }

           
            dot11PortListTable                  	OBJECT-TYPE
            SYNTAX                                  SEQUENCE OF Dot11PortListEntry
            ACCESS                                  not-accessible
            STATUS                                  mandatory
            DESCRIPTION
            ""
            ::= { dot11PortListRecord 2 }   
  
            
            
            dot11PortListEntry              		OBJECT-TYPE
            SYNTAX                                  Dot11PortListEntry
            ACCESS                                  not-accessible
            STATUS                                  mandatory
            DESCRIPTION
            ""
            INDEX                                   { dot11PortListIndex}
            ::= { dot11PortListTable 1 }

            Dot11PortListEntry
            ::= SEQUENCE {
                dot11PortListIndex            	INTEGER,
                dot11PortListTagVid             OCTET STRING,
                dot11PortListUntagVid           OCTET STRING,
                dot11PortLisPortName			OCTET STRING           
            }  
            
            dot11PortListIndex             			OBJECT-TYPE
            SYNTAX                                  INTEGER
            ACCESS                                  not-accessible
            STATUS                                  mandatory
            DESCRIPTION
            ""
            ::= { dot11PortListEntry 1 }

 	   		dot11PortListTagVid 					OBJECT-TYPE
            SYNTAX                                  OCTET STRING
            ACCESS                                  read-only
            STATUS                                  mandatory
            DESCRIPTION
            ""
            ::= { dot11PortListEntry 2 }       
               
           dot11PortListUntagVid                	OBJECT-TYPE
            SYNTAX                                  OCTET STRING
            ACCESS                                  read-only
            STATUS                                  mandatory
            DESCRIPTION
            ""
            ::= { dot11PortListEntry 3 }
            
            dot11PortLisPortName                	OBJECT-TYPE
            SYNTAX                                  OCTET STRING
            ACCESS                                  read-only
            STATUS                                  mandatory
            DESCRIPTION
            ""
            ::= { dot11PortListEntry 4 }

               
         ieee802dot11Qos           			OBJECT  IDENTIFIER ::= { advance 7 }
	
			dot11QosStatus               	    	OBJECT-TYPE
            SYNTAX                                  INTEGER {disable(0), enable(1)}
            ACCESS                                  read-write
            STATUS                                  mandatory
            DESCRIPTION
            ""
            ::= { ieee802dot11Qos 1 }



            dot11QosPriorityClassifiers             OBJECT  IDENTIFIER ::= { ieee802dot11Qos 2 }

            dot11QosHttp	               	    	OBJECT-TYPE
            SYNTAX                                  INTEGER {disable(0), enable(1)}
            ACCESS                                  read-write
            STATUS                                  mandatory
            DESCRIPTION
            ""
            ::= { dot11QosPriorityClassifiers 1 }

            dot11QosAutomatic                       OBJECT-TYPE
            SYNTAX                                  INTEGER {disable(0), enable(1)}
            ACCESS                                 read-write
            STATUS                                  mandatory
            DESCRIPTION
            ""
            ::= { dot11QosPriorityClassifiers 2 } 
		
	    	dot11QosRuleStatus                       OBJECT-TYPE
            SYNTAX                                  INTEGER {disable(0), enable(1)}
            ACCESS                                  read-write
            STATUS                                  mandatory
            DESCRIPTION
            ""
            ::= { dot11QosPriorityClassifiers 3 }   
            
            dot11QosRulesDelete           			OBJECT-TYPE
            SYNTAX                                  INTEGER(1..64) 
            ACCESS                                  read-write
            STATUS                                  mandatory
            DESCRIPTION
            ""
            ::= { dot11QosPriorityClassifiers 4 }

            
            dot11QosRulesTable                 	    OBJECT-TYPE
            SYNTAX                                  SEQUENCE OF Dot11QosRulesEntry
            ACCESS                                  not-accessible
            STATUS                                  mandatory
            DESCRIPTION
            ""
            ::= { dot11QosPriorityClassifiers  5 }  
            
            dot11QosRulesEntry                 	    OBJECT-TYPE
            SYNTAX                                  Dot11QosRulesEntry
            ACCESS                                  not-accessible
            STATUS                                  mandatory
            DESCRIPTION
            ""
            INDEX                                   { dot11QosRulesIndex }
            ::= { dot11QosRulesTable  1 }

            Dot11QosRulesEntry
            ::= SEQUENCE {     
            	dot11QosRulesIndex            	INTEGER,
                dot11QosRulesState              INTEGER,
                dot11QosRulesName             	OCTET STRING,
                dot11QosRulesPriority           INTEGER,
                dot11QosRulesProtocol           INTEGER,
                dot11QosRulesProtocolType       INTEGER,
                dot11QosRulesHostOneIpStart          	IpAddress,
                dot11QosRulesHostOneIpEnd           	IpAddress,
                dot11QosRulesHostOneIpRange           	INTEGER,
                dot11QosRulesHostOnePortStart          	INTEGER,
				dot11QosRulesHostOnePortEnd           	INTEGER,
				dot11QosRulesHostOnePortRange          	INTEGER,
				dot11QosRulesHostTwoIpStart          	IpAddress,
                dot11QosRulesHostTwoIpEnd           	IpAddress,
                dot11QosRulesHostTwoIpRange           	INTEGER,
                dot11QosRulesHostTwoPortStart          	INTEGER,
				dot11QosRulesHostTwoPortEnd           	INTEGER,
				dot11QosRulesHostTwoPortRange          	INTEGER
            }
            dot11QosRulesIndex              	    OBJECT-TYPE
            SYNTAX                                  INTEGER
            ACCESS                                  not-accessible
            STATUS                                  mandatory
            DESCRIPTION
            ""
            ::= { dot11QosRulesEntry 1 }  
            
            
            dot11QosRulesState                      OBJECT-TYPE
            SYNTAX                                  INTEGER {disable(0), enable(1)}
            ACCESS                                  read-write
            STATUS                                  mandatory
            DESCRIPTION
            ""
            ::= { dot11QosRulesEntry 2 }

          
	
	    	dot11QosRulesName                       OBJECT-TYPE
            SYNTAX                                  OCTET STRING (SIZE(0..64))
            ACCESS                                  read-write
            STATUS                                  mandatory
            DESCRIPTION
            ""
            ::= { dot11QosRulesEntry 3 }


            dot11QosRulesPriority                    OBJECT-TYPE
            SYNTAX                                  INTEGER {vo(0),vi(1),be(2),bk(3)}
            ACCESS                                  read-write
            STATUS                                  mandatory
            DESCRIPTION
            ""
            ::= { dot11QosRulesEntry 4 }

            dot11QosRulesProtocol              		OBJECT-TYPE
            SYNTAX                                  INTEGER (0..256)
            ACCESS                                  read-write
            STATUS                                  mandatory
            DESCRIPTION
            ""
            ::= { dot11QosRulesEntry 5 }

            dot11QosRulesProtocolType          		OBJECT-TYPE
            SYNTAX                                  INTEGER{any(0),tcp(1),udp(2),both(3),icmp(4),other(5)} 
            ACCESS                                  read-write
            STATUS                                  mandatory
            DESCRIPTION
            ""
            ::= { dot11QosRulesEntry 6 }

            dot11QosRulesHostOneIpStart          	OBJECT-TYPE
            SYNTAX                                  IpAddress
            ACCESS                                  read-write
            STATUS                                  mandatory
            DESCRIPTION
            ""
            ::= { dot11QosRulesEntry 7 }
	   
	    	dot11QosRulesHostOneIpEnd           	OBJECT-TYPE
            SYNTAX                                  IpAddress
            ACCESS                                  read-write
            STATUS                                  mandatory
            DESCRIPTION
            ""
            ::= { dot11QosRulesEntry 8 }
		
            dot11QosRulesHostOneIpRange           	OBJECT-TYPE
            SYNTAX                                  INTEGER 
            ACCESS                                  read-write
            STATUS                                  mandatory
            DESCRIPTION
            ""
            ::= { dot11QosRulesEntry 9 }

	   		dot11QosRulesHostOnePortStart          	OBJECT-TYPE
            SYNTAX                                  INTEGER 
            ACCESS                                  read-write
            STATUS                                  mandatory
            DESCRIPTION
            ""
            ::= { dot11QosRulesEntry 10 }

	 		dot11QosRulesHostOnePortEnd           	OBJECT-TYPE
            SYNTAX                                  INTEGER 
            ACCESS                                  read-write
            STATUS                                  mandatory
            DESCRIPTION
            ""
            ::= { dot11QosRulesEntry 11 }

	 		dot11QosRulesHostOnePortRange           OBJECT-TYPE
            SYNTAX                                  INTEGER 
            ACCESS                                  read-write
            STATUS                                  mandatory
            DESCRIPTION
            ""
            ::= { dot11QosRulesEntry 12 } 
            
            dot11QosRulesHostTwoIpStart          	OBJECT-TYPE
            SYNTAX                                  IpAddress
            ACCESS                                  read-write
            STATUS                                  mandatory
            DESCRIPTION
            ""
            ::= { dot11QosRulesEntry 13 }
	   
	    	dot11QosRulesHostTwoIpEnd           	OBJECT-TYPE
            SYNTAX                                  IpAddress
            ACCESS                                  read-write
            STATUS                                  mandatory
            DESCRIPTION
            ""
            ::= { dot11QosRulesEntry 14 }
		
            dot11QosRulesHostTwoIpRange           	OBJECT-TYPE
            SYNTAX                                  INTEGER 
            ACCESS                                  read-write
            STATUS                                  mandatory
            DESCRIPTION
            ""
            ::= { dot11QosRulesEntry 15 }

	   		dot11QosRulesHostTwoPortStart          	OBJECT-TYPE
            SYNTAX                                  INTEGER 
            ACCESS                                  read-write
            STATUS                                  mandatory
            DESCRIPTION
            ""
            ::= { dot11QosRulesEntry 16 }

	 		dot11QosRulesHostTwoPortEnd           	OBJECT-TYPE
            SYNTAX                                  INTEGER 
            ACCESS                                  read-write
            STATUS                                  mandatory
            DESCRIPTION
            ""
            ::= { dot11QosRulesEntry 17 }

	 		dot11QosRulesHostTwoPortRange           OBJECT-TYPE
            SYNTAX                                  INTEGER 
            ACCESS                                  read-write
            STATUS                                  mandatory
            DESCRIPTION
            ""
            ::= { dot11QosRulesEntry 18 }  
            
             --capwap           			OBJECT  IDENTIFIER ::= { advance 8 }

			--capwapWlanSwitchSetting                      OBJECT  IDENTIFIER ::= { capwap 1 }
	
			--capwapWtpStatus               	    		OBJECT-TYPE
            --SYNTAX                                  INTEGER {disable(0), enable(1)}
            --ACCESS                                  read-write
            --STATUS                                  mandatory
            --DESCRIPTION
            --""
            --::= { capwapWlanSwitchSetting 1 }

			--capwapWtpName               	    			OBJECT-TYPE
            --SYNTAX                                  OCTET STRING
            --ACCESS                                  read-only
            --STATUS                                  mandatory
            --DESCRIPTION
            --""
            --::= { capwapWlanSwitchSetting 2 }

			--capwapWtpLocationData               	    	OBJECT-TYPE
            --SYNTAX                                  OCTET STRING
            --ACCESS                                  read-only
            --STATUS                                  mandatory
            --DESCRIPTION
            --""
            --::= { capwapWlanSwitchSetting 3 }

			--capwapWtpConnectingSwitchIP              		OBJECT-TYPE
            --SYNTAX                                  IpAddress
            --ACCESS                                  read-only
           -- STATUS                                  mandatory
            --DESCRIPTION
            --""
            --::= {capwapWlanSwitchSetting 4 }

			--capwapWtpConnectingSwitchName            OBJECT-TYPE
            --SYNTAX                                  OCTET STRING
            --ACCESS                                  read-only
            --STATUS                                  mandatory
            --DESCRIPTION
            --""
            --::= { capwapWlanSwitchSetting 5 }

			--capwapWtpSwitchIpAddressDelete             OBJECT-TYPE
            --SYNTAX                                  INTEGER (1..64)
            --ACCESS                                  read-write
            --STATUS                                  mandatory
            --DESCRIPTION
            --""
            --::= { capwapWlanSwitchSetting 6 }

			--capwapWtpSwitchIpAddressAdd               	OBJECT-TYPE
            --SYNTAX                                  IpAddress
            --ACCESS                                  read-write
            --STATUS                                  mandatory
            --DESCRIPTION
            --""
            --::= { capwapWlanSwitchSetting 7 }


 
            --wtpSwitchAddressListTable            	OBJECT-TYPE
            --SYNTAX                                  SEQUENCE OF WtpSwitchAddressListEntry
            --ACCESS                                  not-accessible
            --STATUS                                  mandatory
            --DESCRIPTION
            --""
            --::= { capwapWlanSwitchSetting 8 }

            --wtpSwitchAddressListEntry            	OBJECT-TYPE
            --SYNTAX                                  WtpSwitchAddressListEntry
            --ACCESS                                  not-accessible
            --STATUS                                  mandatory
            --DESCRIPTION
            --""
            --INDEX                                   {wtpSwitchAddressIndex}
            --::= { wtpSwitchAddressListTable 1 }

            --WtpSwitchAddressListEntry
            --::= SEQUENCE {
            --    wtpSwitchAddressIndex        INTEGER,
            --    wtpSwitchIpAddress         IpAddress
            --}

            --wtpSwitchAddressIndex            		OBJECT-TYPE
            -- SYNTAX                                  INTEGER
            --ACCESS                                  not-accessible
            --STATUS                                  mandatory
            --DESCRIPTION
            --""
            --::= { wtpSwitchAddressListEntry 1 }

            --wtpSwitchIpAddress             			OBJECT-TYPE
            --SYNTAX                                  IpAddress
            --ACCESS                                  read-only
           -- STATUS                                  mandatory
            --DESCRIPTION
            --""
            --::= { wtpSwitchAddressListEntry 2 }


         -- ieee802dot11TrafficControl           			OBJECT  IDENTIFIER ::= { advance 9 }
			-- dot11UpDownLinksetting                      OBJECT  IDENTIFIER ::= { ieee802dot11TrafficControl 1 }
			-- dot11TrafficcontrolInterface				OBJECT  IDENTIFIER ::= { dot11UpDownLinksetting 1 }

            -- dot11TrafficcontrolInterfaceTable                              OBJECT-TYPE
            -- SYNTAX                                  SEQUENCE OF Dot11TrafficcontrolInterfaceEntry
            -- ACCESS                                  not-accessible
            -- STATUS                                  mandatory
            -- DESCRIPTION
            -- ""
            -- ::= { dot11TrafficcontrolInterface 1 }

            -- dot11TrafficcontrolInterfaceEntry                              OBJECT-TYPE
            -- SYNTAX                                  Dot11TrafficcontrolInterfaceEntry
            -- ACCESS                                  not-accessible
            -- STATUS                                  mandatory
            -- DESCRIPTION
            -- ""
            -- INDEX                                   { dot11TrafficcontrolInterfaceIndex }
            -- ::= { dot11TrafficcontrolInterfaceTable 1 }

            -- Dot11TrafficcontrolInterfaceEntry
            -- ::= SEQUENCE {
                -- dot11TrafficcontrolInterfaceIndex                              INTEGER,
                -- dot11TrafficcontrolInterfaceName                       OCTET STRING,
                -- dot11TrafficcontrolInterfaceMode                          INTEGER
                        -- }

            -- dot11TrafficcontrolInterfaceIndex                              OBJECT-TYPE
            -- SYNTAX                                  INTEGER
            -- ACCESS                                  not-accessible
            -- STATUS                                  mandatory
            -- DESCRIPTION
            -- ""
            -- ::= { dot11TrafficcontrolInterfaceEntry 1 }

            -- dot11TrafficcontrolInterfaceName                               OBJECT-TYPE
            -- SYNTAX                                  OCTET STRING (SIZE(0..32))
            -- ACCESS                                  read-only
            -- STATUS                                  mandatory
            -- DESCRIPTION
            -- ""
            -- ::= { dot11TrafficcontrolInterfaceEntry 2 }

            -- dot11TrafficcontrolInterfaceMode                              OBJECT-TYPE
            -- SYNTAX                                  INTEGER {disable(0),downlink(1),uplink(2)}
            -- ACCESS                                  read-write
            -- STATUS                                  mandatory
            -- DESCRIPTION
            -- ""
            -- ::= { dot11TrafficcontrolInterfaceEntry 3 }
            
                               
	
	    -- dot11TrafficcontrolBandwidth				OBJECT  IDENTIFIER ::= { dot11UpDownLinksetting 2 }
	 		
	    -- dot11DownLinkBandWidth             OBJECT-TYPE
            -- SYNTAX                                  INTEGER
            -- ACCESS                                  read-write
            -- STATUS                                  mandatory
            -- DESCRIPTION
            -- ""
            -- ::= { dot11TrafficcontrolBandwidth 1 }

	    -- dot11UpLinkBandWidth             OBJECT-TYPE
            -- SYNTAX                                  INTEGER
            -- ACCESS                                  read-write
            -- STATUS                                  mandatory
            -- DESCRIPTION
            -- ""
            -- ::= { dot11TrafficcontrolBandwidth 2 }
            
  

			-- dot11Qos                      OBJECT  IDENTIFIER ::= { ieee802dot11TrafficControl 2 }
			-- dot11QosSetting                      OBJECT  IDENTIFIER ::= { dot11Qos 2 }    
			-- dot11dot11QosStatus                      OBJECT  IDENTIFIER ::= { dot11QosSetting 1 }         
	
	 		-- dot11dot11QosState             OBJECT-TYPE
            -- SYNTAX                                  INTEGER{disable(0),enable(1)}
            -- ACCESS                                  read-write
            -- STATUS                                  mandatory
            -- DESCRIPTION
            -- ""
            -- ::= { dot11dot11QosStatus 1 }
            
			-- dot11QosAdvancedSetting                      OBJECT  IDENTIFIER ::= { dot11QosSetting 2 }

            -- dot11QosAdvancedTable                              OBJECT-TYPE
            -- SYNTAX                                  SEQUENCE OF Dot11QosAdvancedEntry
            -- ACCESS                                  not-accessible
            -- STATUS                                  mandatory
            -- DESCRIPTION
            -- ""
            -- ::= { dot11QosAdvancedSetting 1 }

            -- dot11QosAdvancedEntry                              OBJECT-TYPE
            -- SYNTAX                                  Dot11QosAdvancedEntry
            -- ACCESS                                  not-accessible
            -- STATUS                                  mandatory
            -- DESCRIPTION
            -- ""
            -- INDEX                                   { dot11QosAdvancedIndex }
            -- ::= { dot11QosAdvancedTable 1 }

            -- Dot11QosAdvancedEntry
            -- ::= SEQUENCE {
                -- dot11QosAdvancedIndex                              INTEGER,
                -- dot11QosAdvancedPriorityName                       OCTET STRING,
                -- dot11QosAdvancedPriority                           INTEGER,
                -- dot11QosAdvancedPriorityLimit                     INTEGER,
                -- dot11QosAdvancedPriorityPort                           OCTET STRING
            -- }

            -- dot11QosAdvancedIndex                              OBJECT-TYPE
            -- SYNTAX                                  INTEGER
            -- ACCESS                                  not-accessible
            -- STATUS                                  mandatory
            -- DESCRIPTION
            -- ""
            -- ::= { dot11QosAdvancedEntry 1 }

            -- dot11QosAdvancedPriorityName                               OBJECT-TYPE
            -- SYNTAX                                  OCTET STRING (SIZE(0..32))
            -- ACCESS                                  read-only
            -- STATUS                                  mandatory
            -- DESCRIPTION
            -- ""
            -- ::= { dot11QosAdvancedEntry 2 }

            -- dot11QosAdvancedPriority                              OBJECT-TYPE
            -- SYNTAX                                  INTEGER {highest(1),second(2),thrid(3),low(4)}
            -- ACCESS                                  read-write
            -- STATUS                                  mandatory
            -- DESCRIPTION
            -- ""
            -- ::= { dot11QosAdvancedEntry 3 }
            
            -- dot11QosAdvancedPriorityLimit                              OBJECT-TYPE
            -- SYNTAX                                  INTEGER
            -- ACCESS                                  read-write
            -- STATUS                                  mandatory
            -- DESCRIPTION
            -- ""
            -- ::= { dot11QosAdvancedEntry 4 }            

            -- dot11QosAdvancedPriorityPort                           OBJECT-TYPE
            -- SYNTAX                                  OCTET STRING (SIZE(0..32))
            -- ACCESS                                  read-write
            -- STATUS                                  mandatory
            -- DESCRIPTION
            -- ""
            -- ::= { dot11QosAdvancedEntry 5 }

			-- dot11TrafficManager                      OBJECT  IDENTIFIER ::= { ieee802dot11TrafficControl 3 } 
			-- dot11TrafficManagerControl               OBJECT  IDENTIFIER ::= { dot11TrafficManager 1 }
	
            -- dot11TrafficManagerStauts                              OBJECT-TYPE
            -- SYNTAX                                  INTEGER{disable(0),enable(1)}
            -- ACCESS                                  read-write
            -- STATUS                                  mandatory
            -- DESCRIPTION
            -- ""
            -- ::= { dot11TrafficManagerControl 1 }            			

            -- dot11TrafficManagerUlistClient                              OBJECT-TYPE
            -- SYNTAX                                  INTEGER{deny(0),forward(1)}
            -- ACCESS                                  read-write
            -- STATUS                                  mandatory
            -- DESCRIPTION
            -- ""
            -- ::= { dot11TrafficManagerControl 2 } 
            
			-- dot11TrafficManagerRule					 OBJECT  IDENTIFIER ::= { dot11TrafficManager 2 }

            -- dot11RuleName                              OBJECT-TYPE
            -- SYNTAX                                  OCTET STRING(SIZE(0..32))
            -- ACCESS                                  read-write
            -- STATUS                                  mandatory
            -- DESCRIPTION
            -- ""
            -- ::= { dot11TrafficManagerRule 1 }            			

            -- dot11ClientIP                              OBJECT-TYPE
            -- SYNTAX                                  IpAddress        
            -- ACCESS                                  read-write
            -- STATUS                                  mandatory
            -- DESCRIPTION
            -- ""
            -- ::= { dot11TrafficManagerRule 2 } 
            -- dot11ClientMac                              OBJECT-TYPE
            -- SYNTAX                                  MacAddress    
            -- ACCESS                                  read-write
            -- STATUS                                  mandatory
            -- DESCRIPTION
            -- ""
            -- ::= { dot11TrafficManagerRule 3 }            			

            -- dot11ClientDownSpeed                              OBJECT-TYPE
            -- SYNTAX                                  INTEGER
            -- ACCESS                                  read-write
            -- STATUS                                  mandatory
            -- DESCRIPTION
            -- ""
            -- ::= { dot11TrafficManagerRule 4 }             

            -- dot11ClientUpSpeed                              OBJECT-TYPE
            -- SYNTAX                                  INTEGER
            -- ACCESS                                  read-write
            -- STATUS                                  mandatory
            -- DESCRIPTION
            -- ""
            -- ::= { dot11TrafficManagerRule 5 }             

            -- dot11RuleAction                              OBJECT-TYPE
            -- SYNTAX                                  INTEGER{delete(0),add(1)}
            -- ACCESS                                  read-write
            -- STATUS                                  mandatory
            -- DESCRIPTION
            -- ""
            -- ::= { dot11TrafficManagerRule 6 }             


			
			-- dot11TrafficManagerRulesList					 OBJECT  IDENTIFIER ::= { dot11TrafficManager 3 }			

--            dot11TrafficManagerRulestable                                   OBJECT  IDENTIFIER ::= { dot11TrafficManagerRules 1 }

            -- dot11TrafficManagerRulesListTable                              OBJECT-TYPE
            -- SYNTAX                                  SEQUENCE OF Dot11TrafficManagerRulesListEntry
            -- ACCESS                                  not-accessible
            -- STATUS                                  mandatory
            -- DESCRIPTION
            -- ""
            -- ::= { dot11TrafficManagerRulesList 1 }

            -- dot11TrafficManagerRulesListEntry                              OBJECT-TYPE
            -- SYNTAX                                  Dot11TrafficManagerRulesListEntry
            -- ACCESS                                  not-accessible
            -- STATUS                                  mandatory
            -- DESCRIPTION
            -- ""
            -- INDEX                                   { dot11TrafficManagerRulesListIndex }
            -- ::= { dot11TrafficManagerRulesListTable 1 }

            -- Dot11TrafficManagerRulesListEntry
            -- ::= SEQUENCE {
                -- dot11TrafficManagerRulesListIndex                              INTEGER,
                -- dot11RuleListName                               OCTET STRING,
                -- dot11RuleListClientIP                           IpAddress,
                -- dot11RuleListClientMac                          MacAddress,
                -- dot11RuleListClientDownSpeed                    INTEGER,
                -- dot11RuleListClientUpSpeed                      INTEGER
            -- }

            -- dot11TrafficManagerRulesListIndex                              OBJECT-TYPE
            -- SYNTAX                                  INTEGER
            -- ACCESS                                  not-accessible
            -- STATUS                                  mandatory
            -- DESCRIPTION
            -- ""
            -- ::= { dot11TrafficManagerRulesListEntry 1 }

            -- dot11RuleListName                              OBJECT-TYPE
            -- SYNTAX                                  OCTET STRING(SIZE(0..32))
            -- ACCESS                                  read-write
            -- STATUS                                  mandatory
            -- DESCRIPTION
            -- ""
            -- ::= { dot11TrafficManagerRulesListEntry 2 }            			

            -- dot11RuleListClientIP                              OBJECT-TYPE
            -- SYNTAX                                  IpAddress        
            -- ACCESS                                  read-write
            -- STATUS                                  mandatory
            -- DESCRIPTION
            -- ""
            -- ::= { dot11TrafficManagerRulesListEntry 3 } 

            -- dot11RuleListClientMac                              OBJECT-TYPE
            -- SYNTAX                                  MacAddress    
            -- ACCESS                                  read-write
            -- STATUS                                  mandatory
            -- DESCRIPTION
            -- ""
            -- ::= { dot11TrafficManagerRulesListEntry 4 }            			

            -- dot11RuleListClientDownSpeed                              OBJECT-TYPE
            -- SYNTAX                                  INTEGER
            -- ACCESS                                 read-write
            -- STATUS                                  mandatory
            -- DESCRIPTION
            -- ""
            -- ::= { dot11TrafficManagerRulesListEntry 5 }             

            -- dot11RuleListClientUpSpeed                              OBJECT-TYPE
            -- SYNTAX                                  INTEGER
            -- ACCESS                                 read-write
            -- STATUS                                  mandatory
            -- DESCRIPTION
            -- ""
            -- ::= { dot11TrafficManagerRulesListEntry 6 }         


         ieee802dot11Schedule           			OBJECT  IDENTIFIER ::= { advance 10 }
         ieee802dot11ScheduleSetting           		OBJECT  IDENTIFIER ::= { ieee802dot11Schedule 1 }
		 ieee802dot11ScheduleStatus 	            OBJECT  IDENTIFIER ::= { ieee802dot11ScheduleSetting 1 } 
         dot11ScheduleStatus                              OBJECT-TYPE
            SYNTAX                                  INTEGER{disable(0),enable(1)}
            ACCESS                                  read-write
            STATUS                                  mandatory
            DESCRIPTION
            ""
            ::= { ieee802dot11ScheduleStatus 1 } 
             		 
		 ieee802dot11ScheduleRuleSetting 	            OBJECT  IDENTIFIER ::= { ieee802dot11ScheduleSetting 2 }          
         dot11ScheduleRuleName                              OBJECT-TYPE
            SYNTAX                                  OCTET STRING(SIZE(0..32))
            ACCESS                                  read-write
            STATUS                                  mandatory
            DESCRIPTION
            ""
            ::= { ieee802dot11ScheduleRuleSetting 1 } 

         dot11ScheduleDaysSelect                              OBJECT-TYPE
            SYNTAX                                  INTEGER
            ACCESS                                  read-write
            STATUS                                  mandatory
            DESCRIPTION
            "Sun 1 Mon 2 Tue 4 Wed 8 Thu 16 Fri 32 Sat 64 All week 0"
            ::= { ieee802dot11ScheduleRuleSetting 2 } 
         
         dot11ScheduleAllDaySelect                              OBJECT-TYPE
            SYNTAX                                  INTEGER{disable(0),enable(1)}
            ACCESS                                  read-write
            STATUS                                  mandatory
            DESCRIPTION
            ""
            ::= { ieee802dot11ScheduleRuleSetting 3 }   

         dot11ScheduleRuleStartTime                              OBJECT-TYPE
            SYNTAX                                  OCTET STRING(SIZE(5..5))
            ACCESS                                  read-write
            STATUS                                  mandatory
            DESCRIPTION
            " Please follow this format: 'xx:xx'
              For example: 02:00 "
            ::= { ieee802dot11ScheduleRuleSetting 4 } 

         dot11ScheduleRuleEndTime                              OBJECT-TYPE
            SYNTAX                                  OCTET STRING(SIZE(5..5))
            ACCESS                                  read-write
            STATUS                                  mandatory
            DESCRIPTION
            " Please follow this format: 'xx:xx'
              For example: 23:45 "
            ::= { ieee802dot11ScheduleRuleSetting 5 } 

--         dot11ScheduleWirelessOption                              OBJECT-TYPE
--            SYNTAX                                  INTEGER{off(0),on(1)}
--            ACCESS                                  read-write
--            STATUS                                  mandatory
--            DESCRIPTION
--            ""
--            ::= { ieee802dot11ScheduleRuleSetting 6 } 

         dot11ScheduleAction                              OBJECT-TYPE
            SYNTAX                                  INTEGER{del(0),add(1)}
            ACCESS                                  read-write
            STATUS                                  mandatory
            DESCRIPTION
            ""
            ::= { ieee802dot11ScheduleRuleSetting 7 }                                                

         dot11ScheduleSSIDIndex                              OBJECT-TYPE
            SYNTAX                                  INTEGER(0..3)
            ACCESS                                  read-write
            STATUS                                  mandatory
            DESCRIPTION
            ""
            ::= { ieee802dot11ScheduleRuleSetting 8 }

         dot11ScheduleNodeStatus                              OBJECT-TYPE
            SYNTAX                                  INTEGER{disable(0),enable(1)}
            ACCESS                                  read-write
            STATUS                                  mandatory
            DESCRIPTION
            ""
            ::= { ieee802dot11ScheduleRuleSetting 9 }
		
         dot11ScheduleOverNight                              OBJECT-TYPE
            SYNTAX                                  INTEGER{disable(0),enable(1)}
            ACCESS                                  read-write
            STATUS                                  mandatory
            DESCRIPTION
            ""
            ::= { ieee802dot11ScheduleRuleSetting 10 }
    
		 ieee802dot11ScheduleList           		OBJECT  IDENTIFIER ::= { ieee802dot11Schedule 2 }        
            dot11ScheduleListTable                              OBJECT-TYPE
            SYNTAX                                  SEQUENCE OF Dot11ScheduleListEntry
            ACCESS                                  not-accessible
            STATUS                                  mandatory
            DESCRIPTION
            ""
            ::= { ieee802dot11ScheduleList 1 }

            dot11ScheduleListEntry                              OBJECT-TYPE
            SYNTAX                                  Dot11ScheduleListEntry
            ACCESS                                  not-accessible
            STATUS                                  mandatory
            DESCRIPTION
            ""
            INDEX                                   { dot11ScheduleListIndex }
            ::= { dot11ScheduleListTable 1 }

            Dot11ScheduleListEntry
            ::= SEQUENCE {
                dot11ScheduleListIndex                              INTEGER,   
                dot11ScheduleListName                               OCTET STRING,
				dot11ScheduleListSSIDIndex						INTEGER,
				dot11ScheduleListSSID						OCTET STRING,
                dot11ScheduleListDays                           OCTET STRING,
                dot11ScheduleListTimeFrame                      OCTET STRING,
                dot11ScheduleListWirelessStatus                      INTEGER,
                dot11ScheduleListNodeStatus						INTEGER,
		        dot11ScheduleListOverNight						INTEGER		
            }

            dot11ScheduleListIndex                              OBJECT-TYPE
            SYNTAX                                  INTEGER
            ACCESS                                  not-accessible
            STATUS                                  mandatory
            DESCRIPTION
            ""
            ::= { dot11ScheduleListEntry 1 }

            dot11ScheduleListName                              OBJECT-TYPE
            SYNTAX                                  OCTET STRING(SIZE(0..32))
            ACCESS                                  read-write
            STATUS                                  mandatory
            DESCRIPTION
            ""
            ::= { dot11ScheduleListEntry 2 }            			

            dot11ScheduleListDays                              OBJECT-TYPE
            SYNTAX                                  OCTET STRING(SIZE(0..32))        
            ACCESS                                  read-write
            STATUS                                  mandatory
            DESCRIPTION
            ""
            ::= { dot11ScheduleListEntry 3 } 

            dot11ScheduleListTimeFrame                              OBJECT-TYPE
            SYNTAX                                  OCTET STRING(SIZE(0..32))    
            ACCESS                                  read-write
            STATUS                                  mandatory
            DESCRIPTION
            "Please follow this format: 'xx:xx-xx:xx'
              For example: 02:00-24:00, 
              another format is  'allday'  "
            ::= { dot11ScheduleListEntry 4 }            			

            dot11ScheduleListWirelessStatus                              OBJECT-TYPE
            SYNTAX                                  INTEGER{off(0),on(1)}
            ACCESS                                  read-write
            STATUS                                  mandatory
            DESCRIPTION
            ""
            ::= { dot11ScheduleListEntry 5 }             

            dot11ScheduleListSSIDIndex                              OBJECT-TYPE
            SYNTAX                                  INTEGER(0..3)
            ACCESS                                  read-write
            STATUS                                  mandatory
            DESCRIPTION
            ""
            ::= { dot11ScheduleListEntry 6 }

            dot11ScheduleListSSID                              OBJECT-TYPE
            SYNTAX                                  OCTET STRING(SIZE(0..32))
            ACCESS                                  read-write
            STATUS                                  mandatory
            DESCRIPTION
            ""
            ::= { dot11ScheduleListEntry 7 }  
            
            dot11ScheduleListNodeStatus                              OBJECT-TYPE
            SYNTAX                                  INTEGER{disable(0),enable(1)} 
            ACCESS                                  read-write
            STATUS                                  mandatory
            DESCRIPTION
            ""
            ::= { dot11ScheduleListEntry 8 }

            dot11ScheduleListOverNight                              OBJECT-TYPE
            SYNTAX                                  INTEGER{disable(0),enable(1)} 
            ACCESS                                  read-write
            STATUS                                  mandatory
            DESCRIPTION
            ""
            ::= { dot11ScheduleListEntry 9 }
----     
         ieee802dot11APArray           			OBJECT  IDENTIFIER ::= { advance 11 }				         			

         ieee802dot11APArraySetting           		OBJECT  IDENTIFIER ::= { ieee802dot11APArray 1 }
		 ieee802dot11APArrayStatus 	            OBJECT  IDENTIFIER ::= { ieee802dot11APArraySetting 1 } 

         dot11APArrayStatus                              OBJECT-TYPE
            SYNTAX                                  INTEGER{disable(0),enable(1)}
            ACCESS                                  read-write
            STATUS                                  mandatory
            DESCRIPTION
            ""
            ::= { ieee802dot11APArrayStatus 1 } 

         dot11APArrayModeSelect                              OBJECT-TYPE
            SYNTAX                                  INTEGER{master(1),masterbackup(2),slave(3)}
            ACCESS                                  read-write
            STATUS                                  mandatory
            DESCRIPTION
            ""
            ::= { ieee802dot11APArrayStatus 2 }  
            
         dot11ApArrayName                              OBJECT-TYPE
            SYNTAX                                  OCTET STRING(SIZE(0..32))
            ACCESS                                  read-write
            STATUS                                  mandatory
            DESCRIPTION
            ""
            ::= { ieee802dot11APArrayStatus 3 } 

         dot11ApArrayPassword                              OBJECT-TYPE
            SYNTAX                                  OCTET STRING(SIZE(0..64))
            ACCESS                                  read-write
            STATUS                                  mandatory
            DESCRIPTION
            ""
            ::= { ieee802dot11APArrayStatus 4 }              
				
		dot11ApArrayVersionNumber                             OBJECT-TYPE
            SYNTAX                                  OCTET STRING(SIZE(0..32))
            ACCESS                                  read-only
            STATUS                                  mandatory
            DESCRIPTION
            ""
            ::= { ieee802dot11APArrayStatus 5 }    
       
	ieee802dot11APArrayScans 	            OBJECT  IDENTIFIER ::= { ieee802dot11APArraySetting 2 }          

	ieee802dot11APArrayScanSetting 	            OBJECT  IDENTIFIER ::= { ieee802dot11APArrayScans 1 } 
  
         dot11ApArrayScan                             OBJECT-TYPE
            SYNTAX                                  INTEGER { nothing(0),refresh(1) }
            ACCESS                                  read-write
            STATUS                                  mandatory
            DESCRIPTION
            ""
            ::= { ieee802dot11APArrayScanSetting 1 }   
              
            dot11ApArrayScanStatus                             OBJECT-TYPE
            SYNTAX                                  INTEGER { disable(0),enable(1) }
            ACCESS                                  read-only
            STATUS                                  mandatory
            DESCRIPTION
            ""
            ::= { ieee802dot11APArrayScanSetting 2 } 
              
	ieee802dot11APArrayScanList           		OBJECT  IDENTIFIER ::= { ieee802dot11APArrayScanSetting 3 }        

            dot11APArrayScanListTable                              OBJECT-TYPE
            SYNTAX                                  SEQUENCE OF Dot11APArrayScanListEntry
            ACCESS                                  not-accessible
            STATUS                                  mandatory
            DESCRIPTION
            ""
            ::= { ieee802dot11APArrayScanList 1 }

            dot11APArrayScanListEntry                              OBJECT-TYPE
            SYNTAX                                  Dot11APArrayScanListEntry
            ACCESS                                  not-accessible
            STATUS                                  mandatory
            DESCRIPTION
            ""
            INDEX                                   { dot11APArrayScanListIndex }
            ::= { dot11APArrayScanListTable 1 }

            Dot11APArrayScanListEntry
            ::= SEQUENCE {
                dot11APArrayScanListIndex                              INTEGER,
                dot11APArrayScanListName                               OCTET STRING,
                dot11APArrayScanListMasterIP                           IpAddress,
                dot11APArrayScanListMac                      MacAddress,
                dot11APArrayScanListMasterNumber                      INTEGER,
                dot11APArrayScanListBackupNumber                      INTEGER,
                dot11APArrayScanListSlaverNumber                      INTEGER,
                dot11APArrayScanListTotal                      INTEGER
            }

            dot11APArrayScanListIndex                              OBJECT-TYPE
            SYNTAX                                  INTEGER
            ACCESS                                  not-accessible
            STATUS                                  mandatory
            DESCRIPTION
            ""
            ::= { dot11APArrayScanListEntry 1 }

            dot11APArrayScanListName                              OBJECT-TYPE
            SYNTAX                                  OCTET STRING(SIZE(0..32))
            ACCESS                                  read-only
            STATUS                                  mandatory
            DESCRIPTION
            ""
            ::= { dot11APArrayScanListEntry 2 }            			

            dot11APArrayScanListMasterIP                              OBJECT-TYPE
            SYNTAX                                 IpAddress        
            ACCESS                                  read-only
            STATUS                                  mandatory
            DESCRIPTION
            ""
            ::= { dot11APArrayScanListEntry 3 } 

            dot11APArrayScanListMac                              OBJECT-TYPE
            SYNTAX                                  MacAddress    
            ACCESS                                  read-only
            STATUS                                  mandatory
            DESCRIPTION
            ""
            ::= { dot11APArrayScanListEntry 4 }            			

            dot11APArrayScanListMasterNumber                OBJECT-TYPE
            SYNTAX                                  INTEGER
            ACCESS                                  read-only
            STATUS                                  mandatory
            DESCRIPTION
            ""
            ::= { dot11APArrayScanListEntry 5 }    
            
            dot11APArrayScanListBackupNumber                OBJECT-TYPE
            SYNTAX                                  INTEGER
            ACCESS                                  read-only
            STATUS                                  mandatory
            DESCRIPTION
            ""
            ::= { dot11APArrayScanListEntry 6 } 

            dot11APArrayScanListSlaverNumber                OBJECT-TYPE
            SYNTAX                                  INTEGER
            ACCESS                                  read-only
            STATUS                                  mandatory
            DESCRIPTION
            ""
            ::= { dot11APArrayScanListEntry 7 } 
            
            dot11APArrayScanListTotal                OBJECT-TYPE
            SYNTAX                                  INTEGER
            ACCESS                                  read-only
            STATUS                                  mandatory
            DESCRIPTION
            ""
            ::= { dot11APArrayScanListEntry 8 } 
            
		 ieee802dot11APArrayMeberList           		OBJECT  IDENTIFIER ::= { ieee802dot11APArray 2 }        

            dot11APArrayMeberListTable                              OBJECT-TYPE
            SYNTAX                                  SEQUENCE OF Dot11APArrayMeberListEntry
            ACCESS                                  not-accessible
            STATUS                                  mandatory
            DESCRIPTION
            ""
            ::= { ieee802dot11APArrayMeberList 1 }

            dot11APArrayMeberListEntry                              OBJECT-TYPE
            SYNTAX                                  Dot11APArrayMeberListEntry
            ACCESS                                  not-accessible
            STATUS                                  mandatory
            DESCRIPTION
            ""
            INDEX                                   { dot11APArrayMeberListIndex }
            ::= { dot11APArrayMeberListTable 1 }

            Dot11APArrayMeberListEntry
            ::= SEQUENCE {
                dot11APArrayMeberListIndex                              INTEGER,
        --        dot11APArrayMeberListName                               OCTET STRING,
                dot11APArrayMeberListRole                      		INTEGER,
                dot11APArrayMeberListIP                           IpAddress,
                dot11APArrayMeberListMac                      MacAddress,
                dot11APArrayMeberListLoacation                      OCTET STRING

            }

            dot11APArrayMeberListIndex                              OBJECT-TYPE
            SYNTAX                                  INTEGER
            ACCESS                                  not-accessible
            STATUS                                  mandatory
            DESCRIPTION
            ""
            ::= { dot11APArrayMeberListEntry 1 }

      --      dot11APArrayMeberListName                              OBJECT-TYPE
      --      SYNTAX                                  OCTET STRING(SIZE(0..32))
      --      ACCESS                                  read-only
      --      STATUS                                  mandatory
      --      DESCRIPTION
      --      ""
      --      ::= { dot11APArrayMeberListEntry 2 }            			

            dot11APArrayMeberListRole                OBJECT-TYPE
            SYNTAX                                  INTEGER{master(1),masterbackup(2),slave(3)}
            ACCESS                                  read-only
            STATUS                                  mandatory
            DESCRIPTION
            ""
            ::= { dot11APArrayMeberListEntry 3 } 


            dot11APArrayMeberListIP                              OBJECT-TYPE
            SYNTAX                                 IpAddress        
            ACCESS                                  read-only
            STATUS                                  mandatory
            DESCRIPTION
            ""
            ::= { dot11APArrayMeberListEntry 4 } 

            dot11APArrayMeberListMac                              OBJECT-TYPE
            SYNTAX                                  MacAddress    
            ACCESS                                  read-only
            STATUS                                  mandatory
            DESCRIPTION
            ""
            ::= { dot11APArrayMeberListEntry 5}            			

            dot11APArrayMeberListLoacation                              OBJECT-TYPE
            SYNTAX                                  OCTET STRING(SIZE(0..64))
            ACCESS                                  read-only
            STATUS                                  mandatory
            DESCRIPTION
            ""
            ::= { dot11APArrayMeberListEntry 6 }      
            

		 ieee802dot11APArraySyncParametersStatus           		OBJECT  IDENTIFIER ::= { ieee802dot11APArray 3 }        

            dot11APArraySyncParametersStatusTable                              OBJECT-TYPE
            SYNTAX                                  SEQUENCE OF Dot11APArraySyncParametersStatusEntry
            ACCESS                                  not-accessible
            STATUS                                  mandatory
            DESCRIPTION
            ""
            ::= { ieee802dot11APArraySyncParametersStatus 1 }

            dot11APArraySyncParametersStatusEntry                              OBJECT-TYPE
            SYNTAX                                  Dot11APArraySyncParametersStatusEntry
            ACCESS                                  not-accessible
            STATUS                                  mandatory
            DESCRIPTION
            ""
            INDEX                                   { dot11APArraySyncParametersStatusIndex }
            ::= { dot11APArraySyncParametersStatusTable 1 }

            Dot11APArraySyncParametersStatusEntry
            ::= SEQUENCE {
                dot11APArraySyncParametersStatusIndex                              INTEGER,
                dot11APArraySyncSSIDStatus                                         INTEGER,
                dot11APArraySyncSsidHiddenStatus                                   INTEGER,
                dot11APArraySyncAutoChannelStatus                                   INTEGER,
                dot11APArraySyncChannelWidthStatus                                   INTEGER,
                dot11APArraySyncSecurityStatus                                   INTEGER,
                dot11APArraySyncFixedRateStatus                                   INTEGER,
                dot11APArraySyncBeaconIntervalStatus                                   INTEGER,
                dot11APArraySyncDtimStatus                                   INTEGER,
                dot11APArraySyncTxPowerStatus                                   INTEGER,
                dot11APArraySyncWMMStatus                                   INTEGER,
                dot11APArraySyncAckTimeoutStatus                                   INTEGER,
                dot11APArraySyncShortGIStatus                                   INTEGER,
                dot11APArraySyncIgmpSnoopStatus                                   INTEGER,
                dot11APArraySyncConnectionLimitStatus                                   INTEGER,
                dot11APArraySyncLinkIntegrityStatus                                   INTEGER,
                dot11APArraySyncMultiSsidStatus                                   INTEGER,
                dot11APArraySyncMultiSsidHiddenStatus                                   INTEGER,
                dot11APArraySyncMultiSsidSecurityStatus                                   INTEGER,
                dot11APArraySyncMultiSsidWMMStatus                                   INTEGER,
                dot11APArraySyncQOSStatus                                   INTEGER,
                dot11APArraySyncVlanStatus                                   INTEGER,
                dot11APArraySyncScheduleStatus                                   INTEGER,
                dot11APArraySyncTimeStatus                                   INTEGER,
                dot11APArraySyncLogStatus                                   INTEGER,
                dot11APArraySyncAdminLimitStatus                                   INTEGER,
                dot11APArraySyncSystemStatus                                   INTEGER,
                dot11APArraySyncConsoleProtocolStatus                                   INTEGER,
                dot11APArraySyncSnmpStatus                                   INTEGER,
                dot11APArraySyncPingCtlStatus                                   INTEGER,
                dot11APArraySyncDhcpStatus                                   INTEGER,
                dot11APArraySyncLoginStatus                                   INTEGER,
                dot11APArraySyncAclStatus                                   INTEGER,
                dot11APArraySyncBandStatus                                   INTEGER
            }

            dot11APArraySyncParametersStatusIndex   OBJECT-TYPE
            SYNTAX                                  INTEGER
            ACCESS                                  not-accessible
            STATUS                                  mandatory
            DESCRIPTION
            ""
            ::= { dot11APArraySyncParametersStatusEntry 1 }   
            
            
            dot11APArraySyncSSIDStatus              OBJECT-TYPE
            SYNTAX                                  INTEGER{disable(0),enable(1)}
            ACCESS                                  read-write
            STATUS                                  mandatory
            DESCRIPTION
            ""
            ::= { dot11APArraySyncParametersStatusEntry 2 }      
            
            dot11APArraySyncSsidHiddenStatus              OBJECT-TYPE
            SYNTAX                                  INTEGER{disable(0),enable(1)}
            ACCESS                                  read-write
            STATUS                                  mandatory
            DESCRIPTION
            ""
            ::= { dot11APArraySyncParametersStatusEntry 3 }      
            
            dot11APArraySyncAutoChannelStatus              OBJECT-TYPE
            SYNTAX                                  INTEGER{disable(0),enable(1)}
            ACCESS                                  read-write
            STATUS                                  mandatory
            DESCRIPTION
            ""
            ::= { dot11APArraySyncParametersStatusEntry 4 }      
            

          	dot11APArraySyncChannelWidthStatus               OBJECT-TYPE
            SYNTAX                                  INTEGER{disable(0),enable(1)}
            ACCESS                                  read-write
            STATUS                                  mandatory
            DESCRIPTION
            ""
            ::= { dot11APArraySyncParametersStatusEntry 5 }      
            
      	    dot11APArraySyncSecurityStatus              OBJECT-TYPE
            SYNTAX                                  INTEGER{disable(0),enable(1)}
            ACCESS                                 read-write
            STATUS                                  mandatory
            DESCRIPTION
            ""
            ::= { dot11APArraySyncParametersStatusEntry 6 }      
            
   	        dot11APArraySyncFixedRateStatus               OBJECT-TYPE
            SYNTAX                                  INTEGER{disable(0),enable(1)}
            ACCESS                                  read-write
            STATUS                                  mandatory
            DESCRIPTION
            ""
            ::= { dot11APArraySyncParametersStatusEntry 7 }      
            
            dot11APArraySyncBeaconIntervalStatus               OBJECT-TYPE
            SYNTAX                                  INTEGER{disable(0),enable(1)}
            ACCESS                                  read-write
            STATUS                                  mandatory
            DESCRIPTION
            ""
            ::= { dot11APArraySyncParametersStatusEntry 8 }      
            
            dot11APArraySyncDtimStatus                OBJECT-TYPE
            SYNTAX                                  INTEGER{disable(0),enable(1)}
            ACCESS                                  read-write
            STATUS                                  mandatory
            DESCRIPTION
            ""
            ::= { dot11APArraySyncParametersStatusEntry 9 }      
            
            dot11APArraySyncTxPowerStatus               OBJECT-TYPE
            SYNTAX                                  INTEGER{disable(0),enable(1)}
            ACCESS                                  read-write
            STATUS                                  mandatory
            DESCRIPTION
            ""
            ::= { dot11APArraySyncParametersStatusEntry 10 }      
            
            dot11APArraySyncWMMStatus                OBJECT-TYPE
            SYNTAX                                  INTEGER{disable(0),enable(1)}
            ACCESS                                  read-write
            STATUS                                  mandatory
            DESCRIPTION
            ""
            ::= { dot11APArraySyncParametersStatusEntry 11 }      
            
            dot11APArraySyncAckTimeoutStatus               OBJECT-TYPE
            SYNTAX                                  INTEGER{disable(0),enable(1)}
            ACCESS                                  read-write
            STATUS                                  mandatory
            DESCRIPTION
            ""
            ::= { dot11APArraySyncParametersStatusEntry 12 }      
            
            dot11APArraySyncShortGIStatus               OBJECT-TYPE
            SYNTAX                                  INTEGER{disable(0),enable(1)}
            ACCESS                                  read-write
            STATUS                                  mandatory
            DESCRIPTION
            ""
            ::= { dot11APArraySyncParametersStatusEntry 13 }      
            
            dot11APArraySyncIgmpSnoopStatus                 OBJECT-TYPE
            SYNTAX                                  INTEGER{disable(0),enable(1)}
            ACCESS                                  read-write
            STATUS                                  mandatory
            DESCRIPTION
            ""
            ::= { dot11APArraySyncParametersStatusEntry 14 }      
            
            dot11APArraySyncConnectionLimitStatus                OBJECT-TYPE
            SYNTAX                                  INTEGER{disable(0),enable(1)}
            ACCESS                                  read-write
            STATUS                                  mandatory
            DESCRIPTION
            ""
            ::= { dot11APArraySyncParametersStatusEntry 15 }      
            

            dot11APArraySyncLinkIntegrityStatus                OBJECT-TYPE
            SYNTAX                                  INTEGER{disable(0),enable(1)}
            ACCESS                                  read-write
            STATUS                                  mandatory
            DESCRIPTION
            ""
            ::= { dot11APArraySyncParametersStatusEntry 16 }      
            

            dot11APArraySyncMultiSsidStatus                OBJECT-TYPE
            SYNTAX                                  INTEGER{disable(0),enable(1)}
            ACCESS                                  read-write
            STATUS                                  mandatory
            DESCRIPTION
            ""
            ::= { dot11APArraySyncParametersStatusEntry 17 }      
            
            dot11APArraySyncMultiSsidHiddenStatus                OBJECT-TYPE
            SYNTAX                                  INTEGER{disable(0),enable(1)}
            ACCESS                                  read-write
            STATUS                                  mandatory
            DESCRIPTION
            ""
            ::= { dot11APArraySyncParametersStatusEntry 18 }      
            

            dot11APArraySyncMultiSsidSecurityStatus                OBJECT-TYPE
            SYNTAX                                  INTEGER{disable(0),enable(1)}
            ACCESS                                  read-write
            STATUS                                  mandatory
            DESCRIPTION
            ""
            ::= { dot11APArraySyncParametersStatusEntry 19 }      
            
            dot11APArraySyncMultiSsidWMMStatus                OBJECT-TYPE
            SYNTAX                                  INTEGER{disable(0),enable(1)}
            ACCESS                                  read-write
            STATUS                                  mandatory
            DESCRIPTION
            ""
            ::= { dot11APArraySyncParametersStatusEntry 20 }      
            

            dot11APArraySyncQOSStatus                OBJECT-TYPE
            SYNTAX                                  INTEGER{disable(0),enable(1)}
            ACCESS                                  read-write
            STATUS                                  mandatory
            DESCRIPTION
            ""
            ::= { dot11APArraySyncParametersStatusEntry 21 }      
            
            dot11APArraySyncVlanStatus                 OBJECT-TYPE
            SYNTAX                                  INTEGER{disable(0),enable(1)}
            ACCESS                                  read-write
            STATUS                                  mandatory
            DESCRIPTION
            ""
            ::= { dot11APArraySyncParametersStatusEntry 22 }      
            
            dot11APArraySyncScheduleStatus                 OBJECT-TYPE
            SYNTAX                                  INTEGER{disable(0),enable(1)}
            ACCESS                                  read-write
            STATUS                                  mandatory
            DESCRIPTION
            ""
            ::= { dot11APArraySyncParametersStatusEntry 23 }      
            
            dot11APArraySyncTimeStatus                OBJECT-TYPE
            SYNTAX                                  INTEGER{disable(0),enable(1)}
            ACCESS                                  read-write
            STATUS                                  mandatory
            DESCRIPTION
            ""
            ::= { dot11APArraySyncParametersStatusEntry 24 }      
            
            dot11APArraySyncLogStatus                 OBJECT-TYPE
            SYNTAX                                  INTEGER{disable(0),enable(1)}
            ACCESS                                  read-write
            STATUS                                  mandatory
            DESCRIPTION
            ""
            ::= { dot11APArraySyncParametersStatusEntry 25 }      
            
            dot11APArraySyncAdminLimitStatus                OBJECT-TYPE
            SYNTAX                                  INTEGER{disable(0),enable(1)}
            ACCESS                                  read-write
            STATUS                                  mandatory
            DESCRIPTION
            ""
            ::= { dot11APArraySyncParametersStatusEntry 26 }      
            
            dot11APArraySyncSystemStatus                OBJECT-TYPE
            SYNTAX                                  INTEGER{disable(0),enable(1)}
            ACCESS                                  read-write
            STATUS                                  mandatory
            DESCRIPTION
            ""
            ::= { dot11APArraySyncParametersStatusEntry 27 }      
            
            dot11APArraySyncConsoleProtocolStatus                 OBJECT-TYPE
            SYNTAX                                  INTEGER{disable(0),enable(1)}
            ACCESS                                  read-write
            STATUS                                  mandatory
            DESCRIPTION
            ""
            ::= { dot11APArraySyncParametersStatusEntry 28 }      
            
            dot11APArraySyncSnmpStatus                OBJECT-TYPE
            SYNTAX                                  INTEGER{disable(0),enable(1)}
            ACCESS                                  read-write
            STATUS                                  mandatory
            DESCRIPTION
            ""
            ::= { dot11APArraySyncParametersStatusEntry 29 }      
            
            dot11APArraySyncPingCtlStatus                OBJECT-TYPE
            SYNTAX                                  INTEGER{disable(0),enable(1)}
            ACCESS                                  read-write
            STATUS                                  mandatory
            DESCRIPTION
            ""
            ::= { dot11APArraySyncParametersStatusEntry 30 }      
            

            dot11APArraySyncDhcpStatus                 OBJECT-TYPE
            SYNTAX                                  INTEGER{disable(0),enable(1)}
            ACCESS                                  read-write
            STATUS                                  mandatory
            DESCRIPTION
            ""
            ::= { dot11APArraySyncParametersStatusEntry 31 }      
            
            dot11APArraySyncLoginStatus                 OBJECT-TYPE
            SYNTAX                                  INTEGER{disable(0),enable(1)}
            ACCESS                                  read-write
            STATUS                                  mandatory
            DESCRIPTION
            ""
            ::= { dot11APArraySyncParametersStatusEntry 32 }      
            
            dot11APArraySyncAclStatus                OBJECT-TYPE
            SYNTAX                                  INTEGER{disable(0),enable(1)}
            ACCESS                                  read-write
            STATUS                                  mandatory
            DESCRIPTION
            ""
            ::= { dot11APArraySyncParametersStatusEntry 33 }      
            
            dot11APArraySyncBandStatus            OBJECT-TYPE
            SYNTAX                                  INTEGER{disable(0),enable(1)}
            ACCESS                                  read-write
            STATUS                                  mandatory
            DESCRIPTION
            ""
            ::= { dot11APArraySyncParametersStatusEntry 34 }

--------------
		 -- ieee802LocalRadiusSettings 	            OBJECT  IDENTIFIER ::= { advance 12 }          

		 -- ieee802LocalRadiusSet 	            OBJECT  IDENTIFIER ::= { ieee802LocalRadiusSettings 1 } 

         -- dot11LocalRadiusUserName                              OBJECT-TYPE
            -- SYNTAX                                  OCTET STRING(SIZE(0..32))
            -- ACCESS                                  read-write
            -- STATUS                                  mandatory
            -- DESCRIPTION
            -- ""
            -- ::= { ieee802LocalRadiusSet 1 } 

         -- dot11LocalRadiusPassword                              OBJECT-TYPE
            -- SYNTAX                                  OCTET STRING(SIZE(0..64))
            -- ACCESS                                  read-write
            -- STATUS                                  mandatory
            -- DESCRIPTION
            -- ""
            -- ::= { ieee802LocalRadiusSet 2 }     

         -- dot11LocalRadiusAction                              OBJECT-TYPE
            -- SYNTAX                                  INTEGER{del(0),add(1)}
            -- ACCESS                                  read-write
            -- STATUS                                  mandatory
            -- DESCRIPTION
            -- ""
            -- ::= { ieee802LocalRadiusSet 3 }
             
         -- dot11LocalRadiusNodeStatus					OBJECT-TYPE
            -- SYNTAX                                  INTEGER{disable(0),enable(1)}
            -- ACCESS                                  read-write
            -- STATUS                                  mandatory
            -- DESCRIPTION
            -- ""
            -- ::= { ieee802LocalRadiusSet 4 }
                                       
            
		 -- dot11LocalRadiusInfoList           		OBJECT  IDENTIFIER ::= { ieee802InternalRadiusSettings 2 }        

            -- dot11LocalRadiusInfoTable                              OBJECT-TYPE
            -- SYNTAX                                  SEQUENCE OF Dot11LocalRadiusInfoEntry
            -- ACCESS                                  not-accessible
            -- STATUS                                  mandatory
            -- DESCRIPTION
            -- ""
            -- ::= { dot11LocalRadiusInfoList 1 }

            -- dot11LocalRadiusInfoEntry                              OBJECT-TYPE
            -- SYNTAX                                  Dot11LocalRadiusInfoEntry
            -- ACCESS                                  not-accessible
            -- STATUS                                  mandatory
            -- DESCRIPTION
            -- ""
            -- INDEX                                   { dot11LocalRadiusInfoIndex }
            -- ::= { dot11LocalRadiusInfoTable 1 }

            -- Dot11LocalRadiusInfoEntry
            -- ::= SEQUENCE {
                -- dot11LocalRadiusInfoIndex                              INTEGER,
                -- dot11LocalRadiusInfoName                               OCTET STRING,
                -- dot11LocalRadiusInfoNodeStatus						   INTEGER,
                -- dot11LocalRadiusInfoPasswd							  OCTET STRING
            -- }

            -- dot11LocalRadiusInfoIndex                              OBJECT-TYPE
            -- SYNTAX                                  INTEGER
            -- ACCESS                                  not-accessible
            -- STATUS                                  mandatory
            -- DESCRIPTION
            -- ""
            -- ::= { dot11LocalRadiusInfoEntry 1 }

            -- dot11LocalRadiusInfoName               OBJECT-TYPE
            -- SYNTAX                                  OCTET STRING(SIZE(0..32))
            -- ACCESS                                  read-write
            -- STATUS                                  mandatory
            -- DESCRIPTION
            -- ""
            -- ::= { dot11LocalRadiusInfoEntry 2 }            			

            -- dot11LocalRadiusInfoNodeStatus          OBJECT-TYPE
            -- SYNTAX                                  INTEGER{disable(0),enable(1)}
            -- ACCESS                                  read-write
            -- STATUS                                  mandatory
            -- DESCRIPTION
            -- ""
            -- ::= { dot11LocalRadiusInfoEntry 3 }
            
            -- dot11LocalRadiusInfoPasswd          OBJECT-TYPE
            -- SYNTAX                                  OCTET STRING
            -- ACCESS                                  read-write
            -- STATUS                                  mandatory
            -- DESCRIPTION
            -- ""
            -- ::= { dot11LocalRadiusInfoEntry 4 }
            
                           
            -- parantalControl                    		OBJECT  IDENTIFIER ::= { advance 13 }
                       
            -- parantalControlTable      				OBJECT-TYPE
            -- SYNTAX                                  SEQUENCE OF ParantalControlEntry
            -- ACCESS                                  not-accessible
            -- STATUS                                  mandatory
            -- DESCRIPTION
            -- ""
            -- ::= { parantalControl 1 }     
            
            -- parantalControlEntry            		OBJECT-TYPE
            -- SYNTAX                                  ParantalControlEntry
            -- ACCESS                                  not-accessible
            -- STATUS                                  mandatory
            -- DESCRIPTION
            -- ""
            -- INDEX                                   {ifIndex}
            -- ::= {  parantalControlTable 1 }

             -- ParantalControlEntry
            -- ::= SEQUENCE {
      
					-- parantalControlStatus        	INTEGER,
                	-- parantalControlUrlAdd         	OCTET STRING,
					-- parantalControlUrlDelete        INTEGER
            -- }
			-- parantalControlStatus             		OBJECT-TYPE
            -- SYNTAX                                  INTEGER {disabled(0), allow(1),deny(2)}
            -- ACCESS                                  read-write
            -- STATUS                                  mandatory
            -- DESCRIPTION
            -- ""
            -- ::= { parantalControlEntry 1 }

	    	-- parantalControlUrlAdd             		OBJECT-TYPE
            -- SYNTAX                                  OCTET STRING
            -- ACCESS                                  read-write
            -- STATUS                                  mandatory
            -- DESCRIPTION
            -- ""
            -- ::= { parantalControlEntry 2 }

	    	-- parantalControlUrlDelete         		OBJECT-TYPE
            -- SYNTAX                                  INTEGER(1..10)
            -- ACCESS                                  read-write
            -- STATUS                                  mandatory
            -- DESCRIPTION
            -- ""
            -- ::= { parantalControlEntry 3 }

	         -- parantalControlListTable            	OBJECT-TYPE
            -- SYNTAX                                  SEQUENCE OF ParantalControlListEntry
            -- ACCESS                                  not-accessible
            -- STATUS                                  mandatory
            -- DESCRIPTION
            -- ""
            -- ::= { parantalControl 2 }

            -- parantalControlListEntry            OBJECT-TYPE
            -- SYNTAX                                  ParantalControlListEntry
            -- ACCESS                                  not-accessible
            -- STATUS                                  mandatory
            -- DESCRIPTION
            -- ""
            -- INDEX                                   { parantalControlListIndex}
            -- ::= { parantalControlListTable 1 }

            -- ParantalControlListEntry
            -- ::= SEQUENCE {
                -- parantalControlListIndex        	INTEGER,
				-- parantalControlListUrl       	  OCTET STRING
            -- }

            -- parantalControlListIndex            	OBJECT-TYPE
            -- SYNTAX                                  INTEGER (1..10)
            -- ACCESS                                  not-accessible
            -- STATUS                                  mandatory
            -- DESCRIPTION
            -- ""
            -- ::= { parantalControlListEntry 1 }

	 		-- parantalControlListUrl            		OBJECT-TYPE
            -- SYNTAX                                  OCTET STRING
            -- ACCESS                                  read-only
            -- STATUS                                  mandatory
            -- DESCRIPTION
            -- ""
            -- ::= { parantalControlListEntry 2 }  
----            

--traveller add for web redirection

         	ieee802dot11WebRedirection           			OBJECT  IDENTIFIER ::= { advance 14 }
         	
         	ieee802dot11WebRedirectionSetting           	OBJECT  IDENTIFIER ::= { ieee802dot11WebRedirection 1 }
         					         			
	 		dot11WebRedirectionStatus            		OBJECT-TYPE
            SYNTAX                                  INTEGER{disable(0),enable(1)}
            ACCESS                                  read-write
            STATUS                                  mandatory
            DESCRIPTION
            ""
            ::= { ieee802dot11WebRedirectionSetting 1 }
            
         	ieee802dot11WebRedirectionAccountSetting           			OBJECT  IDENTIFIER ::= { ieee802dot11WebRedirection 2 }
         	
	 		dot11WebRedirectionAccountName            		OBJECT-TYPE
            SYNTAX                                  OCTET STRING
            ACCESS                                  read-write
            STATUS                                  mandatory
            DESCRIPTION
            ""
            ::= { ieee802dot11WebRedirectionAccountSetting 1 }  
   
	 		dot11WebRedirectionAccountPasswd            		OBJECT-TYPE
            SYNTAX                                  OCTET STRING
            ACCESS                                  read-write
            STATUS                                  mandatory
            DESCRIPTION
            ""
            ::= { ieee802dot11WebRedirectionAccountSetting 2 }
            
	 		dot11WebRedirectionAccountStatus            		OBJECT-TYPE
            SYNTAX                                  INTEGER{disable(0),enable(1)}
            ACCESS                                  read-write
            STATUS                                  mandatory
            DESCRIPTION
            ""
            ::= { ieee802dot11WebRedirectionAccountSetting 3 }
            
	 		dot11WebRedirectionAccountAction            		OBJECT-TYPE
            SYNTAX                                  INTEGER{del(0),add(1)}
            ACCESS                                  read-write
            STATUS                                  mandatory
            DESCRIPTION
            ""
            ::= { ieee802dot11WebRedirectionAccountSetting 4 }
            
            
                       
             dot11WebRedirectionAccountTable      				OBJECT-TYPE
             SYNTAX                                  SEQUENCE OF Dot11WebRedirectionAccountEntry
             ACCESS                                  not-accessible
             STATUS                                  mandatory
             DESCRIPTION
             ""
             ::= { ieee802dot11WebRedirectionAccountSetting 5 }     
            
             dot11WebRedirectionAccountEntry            		OBJECT-TYPE
             SYNTAX                                  Dot11WebRedirectionAccountEntry
             ACCESS                                  not-accessible
             STATUS                                  mandatory
             DESCRIPTION
             ""
             INDEX                                   {dot11WebRedirectionIndex}
             ::= {  dot11WebRedirectionAccountTable 1 }

             Dot11WebRedirectionAccountEntry
             ::= SEQUENCE {
      
					 dot11WebRedirectionIndex        	INTEGER,
                	 dot11WebRedirectionListAccountName         	OCTET STRING,
					 dot11WebRedirectionListAccountPasswd        OCTET STRING,
					 dot11WebRedirectionListAccountStatus		INTEGER
             }       
             
            dot11WebRedirectionIndex            		OBJECT-TYPE
            SYNTAX                                   INTEGER
            ACCESS                                  not-accessible
            STATUS                                  mandatory
            DESCRIPTION
            ""
            ::= { dot11WebRedirectionAccountEntry 1 }  
 
                    	
	 		dot11WebRedirectionListAccountName            		OBJECT-TYPE
            SYNTAX                                  OCTET STRING
            ACCESS                                  read-write
            STATUS                                  mandatory
            DESCRIPTION
            ""
            ::= { dot11WebRedirectionAccountEntry 2 }  
   
	 		dot11WebRedirectionListAccountPasswd            		OBJECT-TYPE
            SYNTAX                                  OCTET STRING
            ACCESS                                  read-write
            STATUS                                  mandatory
            DESCRIPTION
            ""
            ::= { dot11WebRedirectionAccountEntry 3 }
            
	 		dot11WebRedirectionListAccountStatus            		OBJECT-TYPE
            SYNTAX                                  INTEGER{disable(0),enable(1)}
            ACCESS                                  read-write
            STATUS                                  mandatory
            DESCRIPTION
            ""
            ::= { dot11WebRedirectionAccountEntry 4 }


  --traveller add for arp spoofing prevention                                     
         	ieee802dot11ARPSpoofingPrevention          			OBJECT  IDENTIFIER ::= { advance 15 }

         	ieee802dot11ARPSpoofingPreventionSetting          	OBJECT  IDENTIFIER ::= { ieee802dot11ARPSpoofingPrevention 1 }

	 		dot11ARPSpoofingPreventionStatus            		OBJECT-TYPE
            SYNTAX                                  INTEGER{disable(0),enable(1)}
            ACCESS                                  read-write
            STATUS                                  mandatory
            DESCRIPTION
            ""
            ::= { ieee802dot11ARPSpoofingPreventionSetting 1 }   
            
         	ieee802dot11ARPSpoofingPreventionAddressSetting     OBJECT  IDENTIFIER ::= { ieee802dot11ARPSpoofingPrevention 2 }
         	
         	
	 		dot11ARPSpoofingPreventionIpAddress            		OBJECT-TYPE
            SYNTAX                                  IpAddress
            ACCESS                                  read-write
            STATUS                                  mandatory
            DESCRIPTION
            ""
            ::= { ieee802dot11ARPSpoofingPreventionAddressSetting 1 } 
            
	 		dot11ARPSpoofingPreventionMacAddress            		OBJECT-TYPE
            SYNTAX                                  MacAddress
            ACCESS                                   read-write
            STATUS                                  mandatory
            DESCRIPTION
            ""
            ::= { ieee802dot11ARPSpoofingPreventionAddressSetting 2 } 
            
            
	 		dot11ARPSpoofingPreventionAction            		OBJECT-TYPE
            SYNTAX                                  INTEGER{del(0),add(1)}
            ACCESS                                  read-write
            STATUS                                  mandatory
            DESCRIPTION
            ""
            ::= { ieee802dot11ARPSpoofingPreventionAddressSetting 3 }             
        
             dot11ARPSpoofingPreventionTable      				OBJECT-TYPE
             SYNTAX                                  SEQUENCE OF Dot11ARPSpoofingPreventionEntry
             ACCESS                                  not-accessible
             STATUS                                  mandatory
             DESCRIPTION
             ""
             ::= { ieee802dot11ARPSpoofingPreventionAddressSetting 4 }     
            
             dot11ARPSpoofingPreventionEntry            		OBJECT-TYPE
             SYNTAX                                  Dot11ARPSpoofingPreventionEntry
             ACCESS                                  not-accessible
             STATUS                                  mandatory
             DESCRIPTION
             ""
             INDEX                                   {dot11ARPSpoofingPreventionIndex}
             ::= {  dot11ARPSpoofingPreventionTable 1 }

             Dot11ARPSpoofingPreventionEntry
             ::= SEQUENCE {      
					 dot11ARPSpoofingPreventionIndex        	INTEGER,
                	 dot11ARPSpoofingPreventionListIpAddress         	IpAddress,
					 dot11ARPSpoofingPreventionListMacAddress        MacAddress
	             }
	             
	 		dot11ARPSpoofingPreventionIndex            		OBJECT-TYPE
            SYNTAX                                  INTEGER
            ACCESS                                  not-accessible
            STATUS                                  mandatory
            DESCRIPTION
            ""
            ::= { dot11ARPSpoofingPreventionEntry 1 }	               
         
	 		dot11ARPSpoofingPreventionListIpAddress            		OBJECT-TYPE
            SYNTAX                                  IpAddress
            ACCESS                                  read-write
            STATUS                                  mandatory
            DESCRIPTION
            ""
            ::= { dot11ARPSpoofingPreventionEntry 2 }	            

	 		dot11ARPSpoofingPreventionListMacAddress            		OBJECT-TYPE
            SYNTAX                                  MacAddress
            ACCESS                                  read-write
            STATUS                                  mandatory
            DESCRIPTION
            ""
            ::= { dot11ARPSpoofingPreventionEntry 3 }	            
---------------------------------------     
            administration                          OBJECT  IDENTIFIER ::= { dap2360B 4 }

            users                                   OBJECT  IDENTIFIER ::= { administration 1 }

            usersTable                              OBJECT-TYPE
            SYNTAX                                  SEQUENCE OF UsersEntry
            ACCESS                                  not-accessible
            STATUS                                  mandatory
            DESCRIPTION
            ""
            ::= { users 1 }

            usersEntry                              OBJECT-TYPE
            SYNTAX                                  UsersEntry
            ACCESS                                  not-accessible
            STATUS                                  mandatory
            DESCRIPTION
            ""
            INDEX                                   { usersIndex }
            ::= { usersTable 1 }

            UsersEntry
            ::= SEQUENCE {
                usersIndex                              INTEGER,
                usersName                               OCTET STRING,
                usersPassword                           OCTET STRING
            }

            usersIndex                              OBJECT-TYPE
            SYNTAX                                  INTEGER
            ACCESS                                  not-accessible
            STATUS                                  mandatory
            DESCRIPTION
            ""
            ::= { usersEntry 1 }

            usersName                               OBJECT-TYPE
            SYNTAX                                  OCTET STRING (SIZE(0..64))
            ACCESS                                  read-write
            STATUS                                  mandatory
            DESCRIPTION
            ""
            ::= { usersEntry 2 }

            usersPassword                           OBJECT-TYPE
            SYNTAX                                  OCTET STRING (SIZE(0..12))
            ACCESS                                  read-write
            STATUS                                  mandatory
            DESCRIPTION
            ""
            ::= { usersEntry 3 }

            device                                  OBJECT  IDENTIFIER ::= { administration 2 }

            deviceRestart                           OBJECT-TYPE
            SYNTAX                                  INTEGER {nothing(0), reboot(1)}
            ACCESS                                  read-write
            STATUS                                  mandatory
            DESCRIPTION
            ""
            ::={ device 1 }

            deviceFactoryDefault                    OBJECT-TYPE
            SYNTAX                                  INTEGER {nothing(0), reset(1)}
            ACCESS                                  read-write
            STATUS                                  mandatory
            DESCRIPTION
            ""
            ::={ device 2 }

            
            deviceSettingApply                    	OBJECT-TYPE
            SYNTAX                                  INTEGER {nothing(0), apply(1)}
            ACCESS                                  read-write
            STATUS                                  mandatory
            DESCRIPTION
            ""
            ::={ device 3 }
            
            deviceSettingDiscard                    	OBJECT-TYPE
            SYNTAX                                  INTEGER {nothing(0), apply(1)}
            ACCESS                                  read-write
            STATUS                                  mandatory
            DESCRIPTION
            ""
            ::={ device 4 }
                      
            languagePackClear                    OBJECT-TYPE
            SYNTAX                                  INTEGER {nothing(0), clear(1)}
            ACCESS                                  read-write
            STATUS                                  mandatory
            DESCRIPTION
            ""
            ::={ device 5 }
      

            update                                  OBJECT  IDENTIFIER ::= { administration 3 }

            updateFirmwareVersion                   OBJECT-TYPE
            SYNTAX                                  OCTET STRING
            ACCESS                                  read-only
            STATUS                                  mandatory
            DESCRIPTION
            ""
            ::= { update 1 }

            tftp                                    OBJECT  IDENTIFIER ::= { update 2 }

            tftpServerIPAddress                     OBJECT-TYPE
            SYNTAX                                  IpAddress
            ACCESS                                  read-write
            STATUS                                  mandatory
            DESCRIPTION
            ""
            ::={ tftp 1 }

            tftpRemoteFileName                      OBJECT-TYPE
            SYNTAX                                  OCTET STRING
            ACCESS                                  read-write
            STATUS                                  mandatory
            DESCRIPTION
            "If put config file. Please follow this format: 'xx.config'
              For example: aaa.config
             If put certificate file. Please follow this format: 'xx.pem'
              For example: aaa.pem "
            ::={ tftp 2 }

          --  tftpLocalFileName                       OBJECT-TYPE
          --  SYNTAX                                  OCTET STRING
          --  ACCESS                                  read-write
         --   STATUS                                  mandatory
         --   DESCRIPTION
         --   ""
         --   ::={ tftp 3 }

            tftpCommand                             OBJECT-TYPE
            SYNTAX                                  INTEGER {connect(1),
                                                             get(2),
                                                             put(3),
                                                             nothing(4),
                                                             putacl(5)
                                                             }
            ACCESS                                  read-write
            STATUS                                  mandatory
            DESCRIPTION
            ""
            ::={ tftp 4 }

            tftpUpgradeSettingCommand               OBJECT-TYPE
            SYNTAX                                  INTEGER {firmwareUpdate(1),
                                                             configSetting(2),
                                                             configSave(3),
                                                             reboot(4),
                                                             factoryReset(5),
                                                             nothing(6),
                                                             certificateFileUpdate(7),
                                                             keyFileUpdate(8),
                                                             getacl(9)
                                                             }
            ACCESS read-write
            STATUS mandatory
            DESCRIPTION
            ""
            ::={ tftp 5 }

            ftp                                     OBJECT  IDENTIFIER ::= { update 3 }

            ftpServerIPAddress                      OBJECT-TYPE
            SYNTAX                                  IpAddress
            ACCESS                                  read-write
            STATUS                                  mandatory
            DESCRIPTION
            ""
            ::={ ftp 1 }

      --      ftpServerPort                           OBJECT-TYPE
      --      SYNTAX                                  INTEGER
      --      ACCESS                                  read-write
      --      STATUS                                  mandatory
      --      DESCRIPTION
      --      ""
      --      ::={ ftp 2 }

            ftpUserName                             OBJECT-TYPE
            SYNTAX                                  OCTET STRING
            ACCESS                                  read-write
            STATUS                                  mandatory
            DESCRIPTION
            ""
            ::={ ftp 3 }

            ftpPassword                             OBJECT-TYPE
            SYNTAX                                  OCTET STRING
            ACCESS                                  read-write
            STATUS                                  mandatory
            DESCRIPTION
            ""
            ::={ ftp 4 }

            ftpRemoteFileName                       OBJECT-TYPE
            SYNTAX                                  OCTET STRING
            ACCESS                                  read-write
            STATUS                                  mandatory
            DESCRIPTION
            "If put config file. Please follow this format: 'xx.config'
              For example: aaa.config
             If put certificate file. Please follow this format: 'xx.pem'
              For example: aaa.pem"
            ::={ ftp 5 }

    --        ftpLocalFileName                        OBJECT-TYPE
    --        SYNTAX                                  OCTET STRING
    --        ACCESS                                  read-write
    --        STATUS                                  mandatory
    --        DESCRIPTION
    --        ""
    --        ::={ ftp 6 }

            ftpCommand                              OBJECT-TYPE
            SYNTAX                                  INTEGER {connect(1),
                                                             get(2),
                                                             put(3),
                                                             nothing(4),
                                                             putacl(5)}
            ACCESS                                  read-write
            STATUS                                  mandatory
            DESCRIPTION
            ""
            ::={ ftp 7 }

     --       discardChanges                          OBJECT-TYPE
     --       SYNTAX                                  INTEGER{nothing(0), discard(1)}
     --       ACCESS                                  read-write
     --       STATUS                                  mandatory
     --       DESCRIPTION
     --       ""
     --       ::= { update 4 }

            ftpUpgradeSettingCommand                OBJECT-TYPE
            SYNTAX                                  INTEGER {firmwareUpdate(1),
                                                             configSetting(2),
                                                             configSave(3),
                                                             reboot(4),
                                                             factoryReset(5),
                                                             nothing(6),
                                                             certificateFileUpdate(7),
                                                             keyFileUpdate(8),
                                                             getacl(9)
                                                             }
            ACCESS read-write
            STATUS mandatory
            DESCRIPTION
            ""
            ::={ ftp 8 }
            
            updateStatus                         OBJECT-TYPE
            SYNTAX				INTEGER {correct(0),
	    						fwSuccess(1),
							wrongImageFile(2),
							wrongConfigFile(3),
            						wrongAclFile(4),
            						configSuccess(5),
            						inProcess(7),
            						failed(8),
            						none(9)
							}
            ACCESS                                  read-only
            STATUS                                  mandatory
            DESCRIPTION
            ""
            ::={ update 6 }

            console                                 OBJECT  IDENTIFIER ::= { administration 4 }

            telnet                                  OBJECT-TYPE
            SYNTAX                                  INTEGER {disabled(0), enabled(1)}
            ACCESS                                  read-write
            STATUS                                  mandatory
            DESCRIPTION
            ""
            ::={ console 1 }

            ssh                                     OBJECT-TYPE
            SYNTAX                                  INTEGER {disabled(0), enabled(1)}
            ACCESS                                  read-write
            STATUS                                  mandatory
            DESCRIPTION
            ""
            ::={ console 2 }

            timeout                                 OBJECT-TYPE
            SYNTAX                                  INTEGER { never(0),
                                                              s60(1),
                                                              s180(2),
                                                              s300(3),
                                                              s600(4),
                                                              s900(5)}
            ACCESS                                  read-write
            STATUS                                  mandatory
            DESCRIPTION
            ""
            ::={ console 3 }

            web                                     OBJECT  IDENTIFIER ::= { administration 5 }

            webStatus                               OBJECT-TYPE
            SYNTAX                                  INTEGER {disabled(0), enabled(1)}
            ACCESS                                  read-write
            STATUS                                  mandatory
            DESCRIPTION
            ""
            ::= { web 1 }

            snmp                                    OBJECT  IDENTIFIER ::= { administration 6 }

            ssl                                     OBJECT  IDENTIFIER ::= { administration 7 }

            sntp                                    OBJECT  IDENTIFIER ::= { administration 8 }

            sntpServerIpAddress                     OBJECT-TYPE
            SYNTAX                                  OCTET STRING
            ACCESS                                  read-write
            STATUS                                  mandatory
            DESCRIPTION
            ""
            ::= { sntp 1 }

            sntpTimeZoneIndex                       OBJECT-TYPE
            SYNTAX                                  INTEGER (1..75)
            ACCESS                                  read-write
            STATUS                                  mandatory
            DESCRIPTION
            ""
            ::= { sntp 2 }

            sntpDayLightSaving                      OBJECT-TYPE
            SYNTAX                                  INTEGER {disabled(0), enabled(1)}
            ACCESS                                  read-write
            STATUS                                  mandatory
            DESCRIPTION
            ""
            ::= { sntp 3 }

            sntpTimeofDay                           OBJECT-TYPE
            SYNTAX                                  OCTET STRING
            ACCESS                                  read-only
            STATUS                                  mandatory
            DESCRIPTION
            ""
            ::= { sntp 4 }

            sntpStatus                              OBJECT-TYPE
            SYNTAX                                  INTEGER {disable(0), enable(1)}
            ACCESS                                  read-write
            STATUS                                  mandatory
            DESCRIPTION
            ""
            ::= { sntp 5 }

            sntpInterval                            OBJECT-TYPE
            SYNTAX                                  INTEGER { one-day(1),
                                                              three-days(2),
                                                              seven-days(3)}
            ACCESS                                  read-write
            STATUS                                  mandatory
            DESCRIPTION
            ""
            ::= { sntp 6 }

            setTimeManually                         OBJECT-TYPE
            SYNTAX                                  OCTET STRING
            ACCESS                                  read-write
            STATUS                                  mandatory
            DESCRIPTION
            " Please follow this format: 'xx-xx-xxxx xx:xx:xx'
              For example: 02-04-1980 14:12:18 "
            ::= { sntp 7 }

            sntpDstStartMonth                       OBJECT-TYPE
            SYNTAX                                  INTEGER(1..12)
            ACCESS                                  read-write
            STATUS                                  mandatory
            DESCRIPTION
            "Jan(1),Feb(2),Mar(3),Apr(4),May(5),Jun(6), 
             Jul(7),Aug(8),Sep(9),Oct(10),Nov(11),Dec(12)"
            ::= { sntp 8 }   
            
            sntpDstStartWeek                        OBJECT-TYPE
            SYNTAX                                  INTEGER(1..5)
            ACCESS                                  read-write
            STATUS                                  mandatory
            DESCRIPTION
            "1st(1),2nd(2),3rd(3),4th(4),5th(5)"
            ::= { sntp 9 }  
            
            sntpDstStartDayOfWeek                  OBJECT-TYPE
            SYNTAX                                  INTEGER{sun(0),
                                                            mon(1),
                                                            tue(2),
                                                            wed(3),
                                                            thu(4),
                                                            fri(5),
                                                            sat(6)}                                                
            ACCESS                                  read-write
            STATUS                                  mandatory
            DESCRIPTION
            ""
            ::= { sntp 10 }  
            
             sntpDstStartCurrentTime                  OBJECT-TYPE
            SYNTAX                                  INTEGER(0..23)                                               
            ACCESS                                  read-write
            STATUS                                  mandatory
            DESCRIPTION
            "0:(12:00 AM) 23:(11:00 PM)"
            ::= { sntp 11 }    
            
              sntpDstEndMonth                       OBJECT-TYPE
            SYNTAX                                  INTEGER(1..12)
            ACCESS                                  read-write
            STATUS                                  mandatory
            DESCRIPTION
            "Jan(1),Feb(2),Mar(3),Apr(4),May(5),Jun(6), 
             Jul(7),Aug(8),Sep(9),Oct(10),Nov(11),Dec(12)"
            ::= { sntp 12 }   
            
            sntpDstEndWeek                        OBJECT-TYPE
            SYNTAX                                  INTEGER(1..5)
            ACCESS                                  read-write
            STATUS                                  mandatory
            DESCRIPTION
            "1st(1),2nd(2),3rd(3),4th(4),5th(5)"
            ::= { sntp 13 }  
            
            sntpDstEndDayOfWeek                  OBJECT-TYPE
            SYNTAX                                  INTEGER{sun(0),
                                                            mon(1),
                                                            tue(2),
                                                            wed(3),
                                                            thu(4),
                                                            fri(5),
                                                            sat(6)}                                                
            ACCESS                                  read-write
            STATUS                                  mandatory
            DESCRIPTION
            ""
            ::= { sntp 14 }  
            
             sntpDstEndCurrentTime                  OBJECT-TYPE
            SYNTAX                                  INTEGER(0..23)                                               
            ACCESS                                  read-write
            STATUS                                  mandatory
            DESCRIPTION
            "0:(12:00 AM) 23:(11:00 PM)"
            ::= { sntp 15 }

            sntpDayLightSavingOffset               OBJECT-TYPE
            SYNTAX                                  INTEGER(0..7)                                               
            ACCESS                                  read-only
            STATUS                                  mandatory
            DESCRIPTION
            "0:(-2:00) 1:(-1:30) 2:(-1:00) 3:(-0:30) 4:(+0:30) 5:(+1:00) 6:(+1:30) 7:(+2:00)"
            ::= { sntp 16 }


            smtp                                    OBJECT  IDENTIFIER ::= { administration 9 }

            smtpStatus                              OBJECT-TYPE
            SYNTAX                                  INTEGER {disable(0), enable(1)}
            ACCESS                                  read-write
            STATUS                                  mandatory
            DESCRIPTION
            ""
            ::= { smtp 1 }

            smtpServerIpAddress                     OBJECT-TYPE
            SYNTAX                                  IpAddress
            ACCESS                                  read-write
            STATUS                                  mandatory
            DESCRIPTION
            ""
            ::= { smtp 2 }

--            smtpSender                              OBJECT-TYPE
--            SYNTAX                                  OCTET STRING
--            ACCESS                                  read-write
--            STATUS                                  mandatory
--            DESCRIPTION
--            ""
--            ::= { smtp 3 }

--            smtpRecipient                           OBJECT-TYPE
--            SYNTAX                                  OCTET STRING
--            ACCESS                                  read-write
--            STATUS                                  mandatory
--            DESCRIPTION
--            ""
--            ::= { smtp 4 }
            
            smtpAccountingName                      OBJECT-TYPE
            SYNTAX                                  OCTET STRING
            ACCESS                                  read-write
            STATUS                                  mandatory
            DESCRIPTION
            ""
            ::= { smtp 5 } 
            
            smtpPassword		                    OBJECT-TYPE
            SYNTAX                                  OCTET STRING
            ACCESS                                  read-write
            STATUS                                  mandatory
            DESCRIPTION
            ""
            ::= { smtp 6 }
            
            limitedAdministrator                    OBJECT IDENTIFIER ::= { administration 10 }

            managerAddress                          OBJECT IDENTIFIER ::= { limitedAdministrator 1 }

            managerIpAddressStatus                  OBJECT-TYPE
            SYNTAX                                  INTEGER {disable(0), vlanID(1), ipaddress(2), both(3)}
            ACCESS                                  read-write
            STATUS                                  mandatory
            DESCRIPTION
            ""
            ::={managerAddress 1}
            
--            managerIpAddressAdd                     OBJECT-TYPE
--            SYNTAX                                  IpAddress
--            ACCESS                                  read-write
--            STATUS                                  mandatory
--            DESCRIPTION
--            ""
--            ::={ managerAddress 2 }
            
            managerIpAddressDelete                  OBJECT-TYPE
            SYNTAX                                  INTEGER(1..4)
            ACCESS                                  read-write
            STATUS                                  mandatory
            DESCRIPTION
            ""
            ::={ managerAddress 3 }
            

            managerIpAddressTable                   OBJECT-TYPE
            SYNTAX                                  SEQUENCE OF ManagerIpAddressEntry
            ACCESS                                  not-accessible
            STATUS                                  mandatory
            DESCRIPTION
            ""
            ::= { managerAddress 4 }

            managerIpAddressEntry                   OBJECT-TYPE
            SYNTAX                                  ManagerIpAddressEntry
            ACCESS                                  not-accessible
            STATUS                                  mandatory
            DESCRIPTION
            ""
            INDEX                                   {managerIpAddressIndex}
            ::= { managerIpAddressTable 1 }

            ManagerIpAddressEntry ::= SEQUENCE {
                managerIpAddressIndex                   INTEGER,
--                managerIpAddress                        IpAddress,
                managerIpAddressPoolStart               IpAddress,
                managerIpAddressPoolEnd               	IpAddress
            }

            managerIpAddressIndex                   OBJECT-TYPE
            SYNTAX                                  INTEGER
            ACCESS                                  not-accessible
            STATUS                                  mandatory
            DESCRIPTION
            ""
            ::= { managerIpAddressEntry 1 }

--            managerIpAddress                        OBJECT-TYPE
--            SYNTAX                                  IpAddress
--            ACCESS                                  read-only
--            STATUS                                  mandatory
--            DESCRIPTION
--            ""
--            ::={ managerIpAddressEntry 2 }   
            
            managerIpAddressPoolStart               OBJECT-TYPE
            SYNTAX                                  IpAddress
            ACCESS                                  read-write
            STATUS                                  mandatory
            DESCRIPTION
            ""
            ::={ managerIpAddressEntry 3 }
            
             managerIpAddressPoolEnd                OBJECT-TYPE
            SYNTAX                                  IpAddress
            ACCESS                                  read-write
            STATUS                                  mandatory
            DESCRIPTION
            ""
            ::={ managerIpAddressEntry 4 }           

            
--            manergeAPwithWLAN                       OBJECT-TYPE
--            SYNTAX                                  INTEGER { disabled(0), enabled(1)}
--            ACCESS                                  read-write
--            STATUS                                  mandatory
--            DESCRIPTION
--            ""
--            ::={ limitedAdministrator 2 }
            
            manergeVLANTag                          OBJECT-TYPE
            SYNTAX                                  INTEGER
            ACCESS                                  read-write
            STATUS                                  mandatory
            DESCRIPTION
            ""
            ::={ limitedAdministrator 3 }

           
--            pingControl                             OBJECT  IDENTIFIER ::= { administration 12 }

--            pingControlStatus                       OBJECT-TYPE
--            SYNTAX                                  INTEGER { disabled(0), enabled(1)}
--            ACCESS                                  read-write
--            STATUS                                  mandatory
--            DESCRIPTION
--            ""
--            ::={ pingControl 1 }


            report                                  OBJECT  IDENTIFIER ::= { dap2360B 5 }

            deviceInformation                       OBJECT  IDENTIFIER  ::= { report 1 }

            deviceInformationFirmwareVersion        OBJECT-TYPE
            SYNTAX                                  OCTET STRING
            ACCESS                                  read-only
            STATUS                                  mandatory
            DESCRIPTION
            ""
            ::= { deviceInformation 1 }

--		deviceInformationCpuUtilization        	OBJECT-TYPE
--            SYNTAX                                  INTEGER
--            ACCESS                                  read-only
--            STATUS                                  mandatory
--            DESCRIPTION
--            ""
--            ::= { deviceInformation 3 }

--	     deviceInformationMemoryUtilization        	OBJECT-TYPE
--            SYNTAX                                  	INTEGER
--            ACCESS                                  	read-only
--            STATUS                                  	mandatory
--            DESCRIPTION
--            ""
--            ::= { deviceInformation 4 }
            
            deviceInformationFirmwareNum        OBJECT-TYPE
            SYNTAX                                  OCTET STRING
            ACCESS                                  read-only
            STATUS                                  mandatory
            DESCRIPTION
            ""
            ::= { deviceInformation 8 }

            interfaceInformation                    OBJECT  IDENTIFIER  ::= { deviceInformation 2 }

            interfaceInformationTable               OBJECT-TYPE
            SYNTAX                                  SEQUENCE OF InterfaceInformationEntry
            ACCESS                                  not-accessible
            STATUS                                  mandatory
            DESCRIPTION
            ""
            ::= { interfaceInformation 1 }

            interfaceInformationEntry               OBJECT-TYPE
            SYNTAX                                  InterfaceInformationEntry
            ACCESS                                  not-accessible
            STATUS                                  mandatory
            DESCRIPTION
            ""
            INDEX                                   {ifIndex}
            ::= { interfaceInformationTable 1 }

            InterfaceInformationEntry
            ::= SEQUENCE
            {
                ifGetIpAddressFrom                      INTEGER,
                ifIpAddress                             IpAddress,
                ifSubnetMask                            IpAddress,
                ifDefaultGateway                        IpAddress,
                ifMacAddress                            MacAddress,
                wirelessLed2dot4G                       INTEGER,
                wirelessLed5G                           INTEGER,
                dataBaseChannel                         INTEGER,
                ssidMacAddressStart                     MacAddress,
                ssidMacAddressEnd                       MacAddress,  
	     	--  mssid1MacAddress        		MacAddress,
	     	--  mssid2MacAddress        		MacAddress,
	     	--  mssid3MacAddress        		MacAddress,
	     	lanLED                                  INTEGER
            }

            ifGetIpAddressFrom                      OBJECT-TYPE
            SYNTAX                                  INTEGER {static(1), dynamic(2)}
            ACCESS                                  read-only
            STATUS                                  mandatory
            DESCRIPTION
            ""
            ::= { interfaceInformationEntry 1 }

            ifIpAddress                             OBJECT-TYPE
            SYNTAX                                  IpAddress
            ACCESS                                  read-only
            STATUS                                  mandatory
            DESCRIPTION
            ""
            ::= { interfaceInformationEntry 2 }

            ifSubnetMask                            OBJECT-TYPE
            SYNTAX                                  IpAddress
            ACCESS                                  read-only
            STATUS                                  mandatory
            DESCRIPTION
            ""
            ::= { interfaceInformationEntry 3 }

            ifDefaultGateway                        OBJECT-TYPE
            SYNTAX                                  IpAddress
            ACCESS                                  read-only
            STATUS                                  mandatory
            DESCRIPTION
            ""
            ::= { interfaceInformationEntry 4 }

            ifMacAddress                            OBJECT-TYPE
            SYNTAX                                  MacAddress
            ACCESS                                  read-only
            STATUS                                  mandatory
            DESCRIPTION
            ""
            ::= { interfaceInformationEntry 5 }

            wirelessLed2dot4G                       OBJECT-TYPE
            SYNTAX                                  INTEGER{disable(0), blinking(1)}
            ACCESS                                  read-only
            STATUS                                  mandatory
            DESCRIPTION
            ""
            ::= { interfaceInformationEntry 6 }      
            
            wirelessLed5G                           OBJECT-TYPE
            SYNTAX                                  INTEGER{disable(0), blinking(1)}
            ACCESS                                  read-only
            STATUS                                  mandatory
            DESCRIPTION
            ""
            ::= { interfaceInformationEntry 7 }

            dataBaseChannel                         OBJECT-TYPE
            SYNTAX                                  INTEGER
            ACCESS                                  read-only
            STATUS                                  mandatory
            DESCRIPTION
            ""
            ::= { interfaceInformationEntry 8 }
            
            ssidMacAddressStart                     OBJECT-TYPE
            SYNTAX                                  MacAddress
            ACCESS                                  read-only
            STATUS                                  mandatory
            DESCRIPTION
            ""
            ::= { interfaceInformationEntry 9 }
        
            ssidMacAddressEnd                       OBJECT-TYPE
            SYNTAX                                  MacAddress
            ACCESS                                  read-only
            STATUS                                  mandatory
            DESCRIPTION
            ""
            ::= { interfaceInformationEntry 10 }
	    
--            mssid1MacAddress                            OBJECT-TYPE
--            SYNTAX                                  MacAddress
--            ACCESS                                  read-only
--            STATUS                                  mandatory
--            DESCRIPTION
--            ""
--            ::= { interfaceInformationEntry 11 }
	    	    
--            mssid2MacAddress                            OBJECT-TYPE
--            SYNTAX                                  MacAddress
--            ACCESS                                  read-only
--            STATUS                                  mandatory
--            DESCRIPTION
--            ""
--            ::= { interfaceInformationEntry 12 }
	    
--            mssid3MacAddress                            OBJECT-TYPE
--            SYNTAX                                  MacAddress
--            ACCESS                                  read-only
--            STATUS                                  mandatory
--            DESCRIPTION
--            ""
--            ::= { interfaceInformationEntry 13 }

            lanLED                                  OBJECT-TYPE
            SYNTAX                                  INTEGER{disable(0), blinking(1)}
            ACCESS                                  read-only
            STATUS                                  mandatory
            DESCRIPTION
            ""
            ::= { interfaceInformationEntry 14 } 	    

            trafficStatistics                       OBJECT  IDENTIFIER  ::= { report 2 }

            trafficStatisticsWired                  OBJECT  IDENTIFIER  ::= { trafficStatistics 1 }

            dot3TrafficStatistics                   OBJECT  IDENTIFIER  ::= { trafficStatisticsWired 1 }

            dot3TrafficStatisticsTable              OBJECT-TYPE
            SYNTAX                                  SEQUENCE OF Dot3TrafficStatisticsEntry
            ACCESS                                  not-accessible
            STATUS                                  mandatory
            DESCRIPTION
            ""
            ::= { dot3TrafficStatistics 1 }

            dot3TrafficStatisticsEntry              OBJECT-TYPE
            SYNTAX                                  Dot3TrafficStatisticsEntry
            ACCESS                                  not-accessible
            STATUS                                  mandatory
            DESCRIPTION
            ""
            INDEX                                   {ifIndex}
            ::= { dot3TrafficStatisticsTable 1 }

            Dot3TrafficStatisticsEntry
            ::= SEQUENCE {
               	dot3TransmittedPacketCount             	INTEGER,
                dot3TransmittedBytesCount          		INTEGER,
                dot3TransmittedDroppedPacketCount		INTEGER,
                dot3ReceivedPacketCount		        	INTEGER,
                dot3ReceivedBytesCount		            INTEGER,
                dot3ReceivedDroppedPacketCount   		INTEGER,
--                dot3ReceivedMulticastPacketCount    	INTEGER,
--                dot3ReceivedBroadcastPacketCount    	INTEGER,
--                dot3Len64PacketCount    				INTEGER,
--                dot3Len65To127PacketCount     			INTEGER,
--                dot3Len128To255PacketCount     			INTEGER,
--                dot3Len256To511PacketCount     		INTEGER,        
--                dot3Len512To1023PacketCount     		INTEGER,
--                dot3Len1024To1518PacketCount    			INTEGER, 
--                dot3Len1519ToMaxPacketCount      		INTEGER,
                dot3Clear							    INTEGER
            }

            dot3TransmittedPacketCount              OBJECT-TYPE
            SYNTAX                                  INTEGER
            ACCESS                                  read-only
            STATUS                                  mandatory
            DESCRIPTION
            ""
            ::= { dot3TrafficStatisticsEntry 1 }

            dot3TransmittedBytesCount               OBJECT-TYPE
            SYNTAX                                  INTEGER
            ACCESS                                  read-only
            STATUS                                  mandatory
            DESCRIPTION
            ""
            ::= { dot3TrafficStatisticsEntry 2 }  
            
            dot3TransmittedDroppedPacketCount       OBJECT-TYPE
            SYNTAX                                  INTEGER
            ACCESS                                  read-only
            STATUS                                  mandatory
            DESCRIPTION
            ""
            ::= { dot3TrafficStatisticsEntry 3 }

			dot3ReceivedPacketCount       			OBJECT-TYPE
            SYNTAX                                  INTEGER
            ACCESS                                  read-only
            STATUS                                  mandatory
            DESCRIPTION
            ""
            ::= { dot3TrafficStatisticsEntry 4 }

			dot3ReceivedBytesCount               	OBJECT-TYPE
            SYNTAX                                  INTEGER
            ACCESS                                  read-only
            STATUS                                  mandatory
            DESCRIPTION
            ""
            ::= { dot3TrafficStatisticsEntry 5 }

            dot3ReceivedDroppedPacketCount	        OBJECT-TYPE
            SYNTAX                                  INTEGER
            ACCESS                                  read-only
            STATUS                                  mandatory
            DESCRIPTION
            ""
            ::= { dot3TrafficStatisticsEntry 6 }
			
--			dot3ReceivedMulticastPacketCount        OBJECT-TYPE
--            SYNTAX                                  INTEGER
--            ACCESS                                  read-only
--            STATUS                                  mandatory
--            DESCRIPTION
--            ""
--            ::= { dot3TrafficStatisticsEntry 7 }

--			dot3ReceivedBroadcastPacketCount        OBJECT-TYPE
--            SYNTAX                                  INTEGER
--            ACCESS                                  read-only
--            STATUS                                  mandatory
--            DESCRIPTION
--            ""
--            ::= { dot3TrafficStatisticsEntry 8 }   
            
--            dot3Len64PacketCount        			OBJECT-TYPE
--            SYNTAX                                  INTEGER
--            ACCESS                                  read-only
--            STATUS                                  mandatory
--            DESCRIPTION
--            ""
--            ::= { dot3TrafficStatisticsEntry 9 }
            
--            dot3Len65To127PacketCount     	        OBJECT-TYPE
--            SYNTAX                                  INTEGER
--            ACCESS                                  read-only
--            STATUS                                  mandatory
--            DESCRIPTION
--            ""
--            ::= { dot3TrafficStatisticsEntry 10 }
            
--            dot3Len128To255PacketCount     	        OBJECT-TYPE
--            SYNTAX                                  INTEGER
--            ACCESS                                  read-only
--            STATUS                                  mandatory
--            DESCRIPTION
--            ""
--            ::= { dot3TrafficStatisticsEntry 11 }
            
--            dot3Len256To511PacketCount    	        OBJECT-TYPE
--            SYNTAX                                  INTEGER
--            ACCESS                                  read-only
--            STATUS                                  mandatory
--            DESCRIPTION
--            ""
--            ::= { dot3TrafficStatisticsEntry 12 }
            
--            dot3Len512To1023PacketCount    	        OBJECT-TYPE
--            SYNTAX                                  INTEGER
--            ACCESS                                  read-only
--            STATUS                                  mandatory
--            DESCRIPTION
--            ""
--            ::= { dot3TrafficStatisticsEntry 13 }   
            
--            dot3Len1024To1518PacketCount             OBJECT-TYPE
--            SYNTAX                                  INTEGER
--            ACCESS                                  read-only
--            STATUS                                  mandatory
--            DESCRIPTION
--            ""
--            ::= { dot3TrafficStatisticsEntry 14 }  
            
--            dot3Len1519ToMaxPacketCount             OBJECT-TYPE
--            SYNTAX                                  INTEGER
--            ACCESS                                  read-only
--            STATUS                                  mandatory
--            DESCRIPTION
--            ""
--            ::= { dot3TrafficStatisticsEntry 15 }  
                       
            dot3Clear								OBJECT-TYPE
            SYNTAX                                  INTEGER {nothing(0), clear(1)}
            ACCESS                                  read-write
            STATUS                                  mandatory
            DESCRIPTION
            ""
            ::= { dot3TrafficStatisticsEntry 16 }            
            
            dot3TrafficStatistics64bits                   OBJECT  IDENTIFIER  ::= { trafficStatisticsWired 2 }

            dot3TrafficStatistics64bitsTable              OBJECT-TYPE
            SYNTAX                                  SEQUENCE OF Dot3TrafficStatistics64bitsEntry
            ACCESS                                  not-accessible
            STATUS                                  mandatory
            DESCRIPTION
            ""
            ::= { dot3TrafficStatistics64bits 1 }

            dot3TrafficStatistics64bitsEntry              OBJECT-TYPE
            SYNTAX                                  Dot3TrafficStatistics64bitsEntry
            ACCESS                                  not-accessible
            STATUS                                  mandatory
            DESCRIPTION
            ""
            INDEX                                   {ifIndex}
            ::= { dot3TrafficStatistics64bitsTable 1 }

            Dot3TrafficStatistics64bitsEntry
            ::= SEQUENCE {
               	dot3TransmittedPacket64bitsCount             	Counter64,  
                dot3TransmittedBytes64bitsCount          		Counter64,
                dot3ReceivedPacket64bitsCount		        	Counter64,
                dot3ReceivedBytes64bitsCount		            Counter64,
                dot3Clear64bits							    	INTEGER
            }
            
            dot3TransmittedPacket64bitsCount          OBJECT-TYPE
			SYNTAX			Counter64
			ACCESS			read-only
			STATUS			mandatory
			DESCRIPTION
			""
			::= { dot3TrafficStatistics64bitsEntry 1 }
			
			dot3TransmittedBytes64bitsCount          OBJECT-TYPE
			SYNTAX			Counter64
			ACCESS			read-only
			STATUS			mandatory
			DESCRIPTION
			""
			::= { dot3TrafficStatistics64bitsEntry 2 }
			
			dot3ReceivedPacket64bitsCount	         OBJECT-TYPE
			SYNTAX			Counter64
			ACCESS			read-only
			STATUS			mandatory
			DESCRIPTION
			""
			::= { dot3TrafficStatistics64bitsEntry 3 }
			
			dot3ReceivedBytes64bitsCount	          OBJECT-TYPE
			SYNTAX			Counter64
			ACCESS			read-only
			STATUS			mandatory
			DESCRIPTION
			""
			::= { dot3TrafficStatistics64bitsEntry 4 }
			
			dot3Clear64bits          OBJECT-TYPE
			SYNTAX			INTEGER
			ACCESS			read-write
			STATUS			mandatory
			DESCRIPTION
			""
			::= { dot3TrafficStatistics64bitsEntry 5 }
			
--			dot3TrafficStatisticsRefresh                         OBJECT-TYPE
--            SYNTAX                                  INTEGER {nothing(0), refresh(1)}
--            ACCESS                                  read-write
--            STATUS                                  mandatory
--            DESCRIPTION
--            ""
--            ::= { trafficStatisticsWired 3 }



            trafficStatisticsWireless               OBJECT  IDENTIFIER  ::= { trafficStatistics 2 }

            dot11TrafficStatistics                  OBJECT  IDENTIFIER  ::= { trafficStatisticsWireless 1 }

            dot11TrafficStatisticsTable             OBJECT-TYPE
            SYNTAX                                  SEQUENCE OF Dot11TrafficStatisticsEntry
            ACCESS                                  not-accessible
            STATUS                                  mandatory
            DESCRIPTION
            ""
            ::= { dot11TrafficStatistics 1 }

            dot11TrafficStatisticsEntry             OBJECT-TYPE
            SYNTAX                                  Dot11TrafficStatisticsEntry
            ACCESS                                  not-accessible
            STATUS                                  mandatory
            DESCRIPTION
            ""
            INDEX                                   {ifIndex}
            ::= { dot11TrafficStatisticsTable 1 }

            Dot11TrafficStatisticsEntry
            ::= SEQUENCE {
                dot11TransmitSuccessRate                INTEGER,
                dot11TransmitRetryRate                  INTEGER,
                -- dot11ReceiveSuccessRate                 INTEGER,
                -- dot11ReceiveDuplicateRate               INTEGER,
                -- dot11RtsSuccessCount                    INTEGER,
                -- dot11RtsFailureCount                    INTEGER,
                -- dot11TransmittedFrameCount              INTEGER,
                -- dot11MulticastTransmittedFrameCount     INTEGER,
                -- dot11TransmittedErrorCount              INTEGER,
                -- dot11TransmittedTotalRetryCount         INTEGER,
                -- dot11TransmittedMultipleRetryCount      INTEGER,
                -- dot11ReceivedFrameCount                 INTEGER,
                -- dot11MulticastReceivedFrameCount        INTEGER,
                -- dot11ReceivedFrameFcsErrorCount         INTEGER,
                -- dot11ReceivedFrameDuplicateCount        INTEGER,
                -- dot11AckReceivedFailureCount            INTEGER,
                -- dot11WepExcludedFrameCount              INTEGER,
                -- dot11WepIcvErrorCount                   INTEGER,
                   dot11TransmittedPacketCount             INTEGER,
                   dot11TransmittedBytesCount          	   INTEGER,
                   dot11TransmittedDroppedPacketCount	   INTEGER,
                   dot11TransmittedRetryCount              INTEGER,
                   dot11ReceivedPacketCount		   INTEGER,
                   dot11ReceivedBytesCount		   INTEGER,
                   dot11ReceivedDroppedPacketCount   	   INTEGER,
                   dot11ReceivedCRCCount        	   INTEGER,
                   dot11ReceivedDecryptionErrorCount       INTEGER,
                   dot11ReceivedMICErrorCount      	   INTEGER,
                   dot11ReceivedPHYErrorCount              INTEGER, 
                   dot11Clear				   INTEGER
            }

            dot11TransmitSuccessRate                OBJECT-TYPE
            SYNTAX                                  INTEGER (0..100)
            ACCESS                                  read-only
            STATUS                                  mandatory
            DESCRIPTION
            ""
            ::= { dot11TrafficStatisticsEntry 1 }

            dot11TransmitRetryRate                  OBJECT-TYPE
            SYNTAX                                  INTEGER (0..100)
            ACCESS                                  read-only
            STATUS                                  mandatory
            DESCRIPTION
            ""
            ::= { dot11TrafficStatisticsEntry 2 }

            -- dot11ReceiveSuccessRate                 OBJECT-TYPE
            -- SYNTAX                                  INTEGER (0..100)
            -- ACCESS                                  read-only
            -- STATUS                                  mandatory
            -- DESCRIPTION
            -- ""
            -- ::= { dot11TrafficStatisticsEntry 3 }

            -- dot11ReceiveDuplicateRate               OBJECT-TYPE
            -- SYNTAX                                  INTEGER (0..100)
            -- ACCESS                                  read-only
            -- STATUS                                  mandatory
            -- DESCRIPTION
            -- ""
            -- ::= { dot11TrafficStatisticsEntry 4 }

            -- dot11RtsSuccessCount                    OBJECT-TYPE
            -- SYNTAX                                  INTEGER
            -- ACCESS                                  read-only
            -- STATUS                                  mandatory
            -- DESCRIPTION
            -- ""
            -- ::= { dot11TrafficStatisticsEntry 5 }

            -- dot11RtsFailureCount                    OBJECT-TYPE
            -- SYNTAX                                  INTEGER
            -- ACCESS                                  read-only
            -- STATUS                                  mandatory
            -- DESCRIPTION
            -- ""
            -- ::= { dot11TrafficStatisticsEntry 6 }

            -- dot11TransmittedFrameCount              OBJECT-TYPE
            -- SYNTAX                                  INTEGER
            -- ACCESS                                  read-only
            -- STATUS                                  mandatory
            -- DESCRIPTION
            -- ""
            -- ::= { dot11TrafficStatisticsEntry 7 }

            -- dot11MulticastTransmittedFrameCount     OBJECT-TYPE
            -- SYNTAX                                  INTEGER
            -- ACCESS                                  read-only
            -- STATUS                                  mandatory
            -- DESCRIPTION
            -- ""
            -- ::= { dot11TrafficStatisticsEntry 8 }

            -- dot11TransmittedErrorCount              OBJECT-TYPE
            -- SYNTAX                                  INTEGER
            -- ACCESS                                  read-only
            -- STATUS                                  mandatory
            -- DESCRIPTION
            -- ""
            -- ::= { dot11TrafficStatisticsEntry 9 }

            -- dot11TransmittedTotalRetryCount         OBJECT-TYPE
            -- SYNTAX                                  INTEGER
            -- ACCESS                                  read-only
            -- STATUS                                  mandatory
            -- DESCRIPTION
            -- ""
            -- ::= { dot11TrafficStatisticsEntry 10 }

            -- dot11TransmittedMultipleRetryCount      OBJECT-TYPE
            -- SYNTAX                                  INTEGER
            -- ACCESS                                  read-only
            -- STATUS                                  mandatory
            -- DESCRIPTION
            -- ""
            -- ::= { dot11TrafficStatisticsEntry 11 }

            -- dot11ReceivedFrameCount                 OBJECT-TYPE
            -- SYNTAX                                  INTEGER
            -- ACCESS                                  read-only
            -- STATUS                                  mandatory
            -- DESCRIPTION
            -- ""
            -- ::= { dot11TrafficStatisticsEntry 12 }

            -- dot11MulticastReceivedFrameCount		OBJECT-TYPE
            -- SYNTAX                                  INTEGER
            -- ACCESS                                  read-only
            -- STATUS                                  mandatory
            -- DESCRIPTION
            -- ""
            -- ::= { dot11TrafficStatisticsEntry 13 }

            -- dot11ReceivedFrameFcsErrorCount		    OBJECT-TYPE
            -- SYNTAX                                  INTEGER
            -- ACCESS                                  read-only
            -- STATUS                                  mandatory
            -- DESCRIPTION
            -- ""
            -- ::= { dot11TrafficStatisticsEntry 14 }

            -- dot11ReceivedFrameDuplicateCount        OBJECT-TYPE
            -- SYNTAX                                  INTEGER
            -- ACCESS                                  read-only
            -- STATUS                                  mandatory
            -- DESCRIPTION
            -- ""
            -- ::= { dot11TrafficStatisticsEntry 15 }

            -- dot11AckReceivedFailureCount	        OBJECT-TYPE
            -- SYNTAX                                  INTEGER
            -- ACCESS                                  read-only
            -- STATUS                                  mandatory
            -- DESCRIPTION
            -- ""
            -- ::= { dot11TrafficStatisticsEntry 16 }

            -- dot11WepExcludedFrameCount              OBJECT-TYPE
            -- SYNTAX                                  INTEGER
            -- ACCESS                                  read-only
            -- STATUS                                  mandatory
            -- DESCRIPTION
            -- ""
            -- ::= { dot11TrafficStatisticsEntry 17 }

            -- dot11WepIcvErrorCount                   OBJECT-TYPE
            -- SYNTAX                                  INTEGER
            -- ACCESS                                  read-only
            -- STATUS                                  mandatory
            -- DESCRIPTION
            -- ""
            -- ::= { dot11TrafficStatisticsEntry 18 }

             
             dot11TransmittedPacketCount             OBJECT-TYPE
             SYNTAX                                  INTEGER 
             ACCESS                                  read-only
             STATUS                                  mandatory
             DESCRIPTION
             ""
            ::= { dot11TrafficStatisticsEntry 19 }

            dot11TransmittedBytesCount              OBJECT-TYPE
            SYNTAX                                  INTEGER 
            ACCESS                                  read-only
            STATUS                                  mandatory
            DESCRIPTION
            ""
            ::= { dot11TrafficStatisticsEntry 20 }

            dot11TransmittedDroppedPacketCount      OBJECT-TYPE
            SYNTAX                                  INTEGER
            ACCESS                                  read-only
            STATUS                                  mandatory
            DESCRIPTION
            ""
            ::= { dot11TrafficStatisticsEntry 21 }

            dot11TransmittedRetryCount              OBJECT-TYPE
            SYNTAX                                  INTEGER 
            ACCESS                                  read-only
            STATUS                                  mandatory
            DESCRIPTION
            ""
            ::= { dot11TrafficStatisticsEntry 22 }

            dot11ReceivedPacketCount              	OBJECT-TYPE
            SYNTAX                                  INTEGER
            ACCESS                                  read-only
            STATUS                                  mandatory
            DESCRIPTION
            ""
            ::= { dot11TrafficStatisticsEntry 23 }

            dot11ReceivedBytesCount	     			OBJECT-TYPE
            SYNTAX                                  INTEGER
            ACCESS                                  read-only
            STATUS                                  mandatory
            DESCRIPTION
            ""
            ::= { dot11TrafficStatisticsEntry 24 }

            dot11ReceivedDroppedPacketCount         OBJECT-TYPE
            SYNTAX                                  INTEGER
            ACCESS                                  read-only
            STATUS                                  mandatory
            DESCRIPTION
            ""
            ::= { dot11TrafficStatisticsEntry 25 }

            dot11ReceivedCRCCount 		   OBJECT-TYPE
            SYNTAX                                  INTEGER
            ACCESS                                  read-only
            STATUS                                  mandatory
            DESCRIPTION
            ""
            ::= { dot11TrafficStatisticsEntry 26 }

            dot11ReceivedDecryptionErrorCount       OBJECT-TYPE
            SYNTAX                                  INTEGER
            ACCESS                                  read-only
            STATUS                                  mandatory
            DESCRIPTION
            ""
            ::= { dot11TrafficStatisticsEntry 27 }
            
            dot11ReceivedMICErrorCount       		OBJECT-TYPE
            SYNTAX                                  INTEGER
            ACCESS                                  read-only
            STATUS                                  mandatory
            DESCRIPTION
            ""
            ::= { dot11TrafficStatisticsEntry 28 }
            
            dot11ReceivedPHYErrorCount              OBJECT-TYPE
            SYNTAX                                  INTEGER
            ACCESS                                  read-only
            STATUS                                  mandatory
            DESCRIPTION
            ""
            ::= { dot11TrafficStatisticsEntry 29 }

            dot11Clear								OBJECT-TYPE
            SYNTAX                                  INTEGER {nothing(0), clear(1)}
            ACCESS                                  read-write
            STATUS                                  mandatory
            DESCRIPTION
            ""
            ::= { dot11TrafficStatisticsEntry 30 }
            
            dot11TrafficStatistics64bits                  OBJECT  IDENTIFIER  ::= { trafficStatisticsWireless 2 }

            dot11TrafficStatistics64bitsTable             OBJECT-TYPE
            SYNTAX                                  SEQUENCE OF Dot11TrafficStatistics64bitsEntry
            ACCESS                                  not-accessible
            STATUS                                  mandatory
            DESCRIPTION
            ""
            ::= { dot11TrafficStatistics64bits 1 }

            dot11TrafficStatistics64bitsEntry             OBJECT-TYPE
            SYNTAX                                  Dot11TrafficStatistics64bitsEntry
            ACCESS                                  not-accessible
            STATUS                                  mandatory
            DESCRIPTION
            ""
            INDEX                                   {ifIndex}
            ::= { dot11TrafficStatistics64bitsTable 1 }

            Dot11TrafficStatistics64bitsEntry
            ::= SEQUENCE {
                   dot11TransmittedPacket64bitsCount            Counter64,
                   dot11TransmittedBytes64bitsCount          	Counter64,  
                   dot11ReceivedPacket64bitsCount		   		Counter64,
                   dot11ReceivedBytes64bitsCount				Counter64,
                   dot11Clear64bits								INTEGER
            }
            
            dot11TransmittedPacket64bitsCount          OBJECT-TYPE
			SYNTAX			Counter64
			ACCESS			read-only
			STATUS			mandatory
			DESCRIPTION
			""
			::= { dot11TrafficStatistics64bitsEntry 1 }
			
			dot11TransmittedBytes64bitsCount          OBJECT-TYPE
			SYNTAX			Counter64
			ACCESS			read-only
			STATUS			mandatory
			DESCRIPTION
			""
			::= { dot11TrafficStatistics64bitsEntry 2 }
			
			dot11ReceivedPacket64bitsCount	         OBJECT-TYPE
			SYNTAX			Counter64
			ACCESS			read-only
			STATUS			mandatory
			DESCRIPTION
			""
			::= { dot11TrafficStatistics64bitsEntry 3 }
			
			dot11ReceivedBytes64bitsCount	          OBJECT-TYPE
			SYNTAX			Counter64
			ACCESS			read-only
			STATUS			mandatory
			DESCRIPTION
			""
			::= { dot11TrafficStatistics64bitsEntry 4 }
			
			dot11Clear64bits          OBJECT-TYPE
			SYNTAX			INTEGER
			ACCESS			read-write
			STATUS			mandatory
			DESCRIPTION
			""
			::= { dot11TrafficStatistics64bitsEntry 5 }
			
--			dot11TrafficStatisticsRefresh                         OBJECT-TYPE
--            SYNTAX                                  INTEGER {nothing(0), refresh(1)}
--            ACCESS                                  read-write
--            STATUS                                  mandatory
--            DESCRIPTION
--            ""
--            ::= { trafficStatisticsWireless 3 }
            
        --    dot16TrafficStatistics                  OBJECT  IDENTIFIER  ::= { trafficStatisticsWireless 3 }

            systemLog                               OBJECT  IDENTIFIER  ::= { report 4 }

            systemLogSystemLevel                    OBJECT-TYPE
            SYNTAX                                  INTEGER {disabled(0), enabled(1)}
            ACCESS                                  read-write
            STATUS                                  mandatory
            DESCRIPTION
            ""
            ::= { systemLog 1 }

            systemLogWirelessLevel                  OBJECT-TYPE
            SYNTAX                                  INTEGER {disabled(0), enabled(1)}
            ACCESS read-write
            STATUS mandatory
            DESCRIPTION  ""
            ::= { systemLog 2 }

            systemLogNoticeLevel                    OBJECT-TYPE
            SYNTAX                                  INTEGER {disabled(0), enabled(1)}
            ACCESS                                  read-write
            STATUS                                  mandatory
            DESCRIPTION
            ""
            ::= { systemLog 3 }

            systemLogTFTPServerIPAddress            OBJECT-TYPE
            SYNTAX                                  IpAddress
            ACCESS                                  read-write
            STATUS                                  mandatory
            DESCRIPTION
            ""
            ::={ systemLog 4 }

            systemLogFileName                       OBJECT-TYPE
            SYNTAX                                  OCTET STRING
            ACCESS                                  read-write
            STATUS                                  mandatory
            DESCRIPTION
            ""
            ::={ systemLog 5 }

            systemLogGetLog                         OBJECT-TYPE
            SYNTAX                                  INTEGER {nothing(0), get(1)}
            ACCESS                                  read-write
            STATUS                                  mandatory
            DESCRIPTION
            ""
            ::={ systemLog 6 }

--            systemLogLocalLogState                  OBJECT-TYPE
--            SYNTAX                                  INTEGER {disabled(0), enabled(1)}
--            ACCESS                                  read-write
--            STATUS                                  mandatory
--            DESCRIPTION
--            ""
--            ::={ systemLog 7 }

            systemLogRemoteLogState                 OBJECT-TYPE
            SYNTAX                                  INTEGER {disabled(0), enabled(1)}
            ACCESS                                  read-write
            STATUS                                  mandatory
            DESCRIPTION
            ""
            ::={ systemLog 8 }

            systemLogServerIPAddress                OBJECT-TYPE
            SYNTAX                                  IpAddress
            ACCESS                                  read-write
            STATUS                                  mandatory
            DESCRIPTION
            ""
            ::={ systemLog 9 }

            systemLogClearLocalLog                  OBJECT-TYPE
            SYNTAX                                  INTEGER {nothing(0), clear(1)}
            ACCESS                                  read-write
            STATUS                                  mandatory
            DESCRIPTION
            ""
            ::={ systemLog 10 }

            emailNotification                       OBJECT  IDENTIFIER  ::= { systemLog 11 }

            emailNotificationTable                  OBJECT-TYPE
            SYNTAX                                  SEQUENCE OF EmailNotificationEntry
            ACCESS                                  not-accessible
            STATUS                                  mandatory
            DESCRIPTION
            ""
            ::= { emailNotification 1 }

            emailNotificationEntry                  OBJECT-TYPE
            SYNTAX                                  EmailNotificationEntry
            ACCESS                                  not-accessible
            STATUS                                  mandatory
            DESCRIPTION
            ""
            INDEX                                   {emailNtfIndex}
            ::= { emailNotificationTable 1 }

            EmailNotificationEntry
            ::= SEQUENCE {
                emailNtfIndex                           INTEGER,
                emailNtfStatus                          INTEGER,
                emailNtfFromIPAddress                   OCTET STRING,
                emailNtfToIPAddress                     OCTET STRING,
                emailNtfServerIPAddress                 OCTET STRING,
                emailNtfAuthentication                  INTEGER,
                emailNtfPassword                        OCTET STRING,
--              emailNtfOnLogFull                       INTEGER,
                emailNtfOnSchedule                      OCTET STRING, 
                emailNtfPort                            INTEGER,
                emailNtfSSL                             INTEGER, 
                emailNtfMailServerIndex                 INTEGER,
                emailNtfUsername                        OCTET STRING               
           }

            emailNtfIndex                           OBJECT-TYPE
            SYNTAX                                  INTEGER
            ACCESS                                  not-accessible
            STATUS                                  mandatory
            DESCRIPTION
            ""
            ::= { emailNotificationEntry 1 }

            emailNtfStatus                          OBJECT-TYPE
            SYNTAX                                  INTEGER { disabled(0), enabled(1) }
            ACCESS                                  read-write
            STATUS                                  mandatory
            DESCRIPTION
            ""
            ::= { emailNotificationEntry 2 }

            emailNtfFromIPAddress                   OBJECT-TYPE
            SYNTAX                                  OCTET STRING
            ACCESS                                  read-write
            STATUS                                  mandatory
            DESCRIPTION
            ""
            ::= { emailNotificationEntry 3 }

            emailNtfToIPAddress                     OBJECT-TYPE
            SYNTAX                                  OCTET STRING
            ACCESS                                  read-write
            STATUS                                  mandatory
            DESCRIPTION
            ""
            ::= { emailNotificationEntry 4 }
            
            emailNtfServerIPAddress                 OBJECT-TYPE
            SYNTAX                                  OCTET STRING
            ACCESS                                  read-write
            STATUS                                  mandatory
            DESCRIPTION
            ""
            ::= { emailNotificationEntry 5 }

            emailNtfAuthentication                  OBJECT-TYPE
            SYNTAX                                  INTEGER{disabled(0), enabled(1)}
            ACCESS                                  read-write
            STATUS                                  mandatory
            DESCRIPTION
            ""
            ::= { emailNotificationEntry 6 }

            emailNtfPassword                        OBJECT-TYPE
            SYNTAX                                  OCTET STRING
            ACCESS                                  read-write
            STATUS                                  mandatory
            DESCRIPTION
            ""
            ::= { emailNotificationEntry 7 }

--            emailNtfOnLogFull                       OBJECT-TYPE
--            SYNTAX                                  INTEGER
--            ACCESS                                  read-write
--            STATUS                                  mandatory
--            DESCRIPTION
--            ""
--            ::= { emailNotificationEntry 8 }
            
            emailNtfOnSchedule                      OBJECT-TYPE
            SYNTAX                                  OCTET STRING
            ACCESS                                  read-write
            STATUS                                  mandatory
            DESCRIPTION
            "0, 0.5, 1, 1.5 ~ 24"
            ::= { emailNotificationEntry 9 }

            emailNtfPort                             OBJECT-TYPE
            SYNTAX                                  INTEGER (0..65535)
            ACCESS                                  read-write
            STATUS                                  mandatory
            DESCRIPTION
            ""
            ::= { emailNotificationEntry 10 } 
            
             emailNtfSSL                             OBJECT-TYPE
            SYNTAX                                  INTEGER {disabled(0), enabled(1)}
            ACCESS                                  read-write
            STATUS                                  mandatory
            DESCRIPTION
            ""
            ::= { emailNotificationEntry 11 }   
            
             emailNtfMailServerIndex                   OBJECT-TYPE
            SYNTAX                                  INTEGER {internal(1), gmail(2),hotmail(3)}
            ACCESS                                  read-write
            STATUS                                  mandatory
            DESCRIPTION
            ""
            ::= { emailNotificationEntry 12 }
            
            emailNtfUsername                        OBJECT-TYPE
            SYNTAX                                  OCTET STRING
            ACCESS                                  read-write
            STATUS                                  mandatory
            DESCRIPTION
            ""
            ::= { emailNotificationEntry 13 }
           
           
--            temperature		                        OBJECT  IDENTIFIER  ::= { report 6 }

      --      systemTemperature                       OBJECT-TYPE
      --      SYNTAX                                  INTEGER
      --      ACCESS                                  read-only
      --      STATUS                                  mandatory
      --      DESCRIPTION
       --     ""
       --     ::= { temperature 1 }

            traps                                   OBJECT  IDENTIFIER  ::= { report 7 }

            trapSetting                             OBJECT  IDENTIFIER  ::= { traps 1 }

            trapStatus                              OBJECT-TYPE
            SYNTAX                                  INTEGER {disabled(0), enabled(1)}
            ACCESS                                  read-write
            STATUS                                  mandatory
            DESCRIPTION
            ""
            ::= { trapSetting 1 }
            
--            trapType                                OBJECT-TYPE
--            SYNTAX                                  INTEGER { normalTrap(0), wirelessTrap(1)}
--            ACCESS                                  read-write
--           STATUS                                  mandatory
--            DESCRIPTION
--            ""
--            ::= { trapSetting 2 }

            trapHostTable                           OBJECT-TYPE
            SYNTAX                                  SEQUENCE OF TrapHostEntry
            ACCESS                                  not-accessible
            STATUS                                  mandatory
            DESCRIPTION
           ""
            ::= { trapSetting 3 }

            trapHostEntry                           OBJECT-TYPE
            SYNTAX                                  TrapHostEntry
            ACCESS                                  not-accessible
            STATUS                                  mandatory
            DESCRIPTION
            ""
            INDEX                                   {trapHostIndex}
            ::= { trapHostTable 1 }

            TrapHostEntry
            ::= SEQUENCE {
                trapHostIndex                           INTEGER,
                trapHostIPAddress                       IpAddress,
                trapVersion                             INTEGER,
                trapSecurityName                        OCTET STRING
            }

            trapHostIndex                           OBJECT-TYPE
            SYNTAX                                  INTEGER
            ACCESS                                  not-accessible
            STATUS                                  mandatory
            DESCRIPTION
            ""
            ::= { trapHostEntry 1 }

            trapHostIPAddress                       OBJECT-TYPE
            SYNTAX                                  IpAddress
            ACCESS                                  read-write
            STATUS                                  mandatory
            DESCRIPTION
            ""
            ::= { trapHostEntry 2 }

             trapVersion                             OBJECT-TYPE
            SYNTAX                                  INTEGER {v1(1), v2c(2), v3(3)}
            ACCESS                                  read-write
            STATUS                                  mandatory
            DESCRIPTION
            ""
            ::= { trapHostEntry 3 }
            
            trapSecurityName                        OBJECT-TYPE
            SYNTAX                                  OCTET STRING
            ACCESS                                  read-write
            STATUS                                  mandatory
            DESCRIPTION
            "v1/v2c: community name, v3: user name"
            ::= { trapHostEntry 4 } 
  
  			trapInstances                           OBJECT  IDENTIFIER  ::= { traps 2 }

            sshLoginFail                            NOTIFICATION-TYPE
            OBJECTS                                 {usersName}
            STATUS                                  current
            DESCRIPTION
            ""
            ::= {trapInstances 1}

            webNotify                               NOTIFICATION-TYPE
            OBJECTS                                 {usersName}
            STATUS                                  current
            DESCRIPTION
            ""
            ::= {trapInstances 2}

            telnetLoginFail                         NOTIFICATION-TYPE
            OBJECTS                                 {usersName}
            STATUS                                  current
            DESCRIPTION
            ""
            ::= {trapInstances 3}

            cpuLoadingFull                          NOTIFICATION-TYPE
            STATUS                                  current
            DESCRIPTION
            ""
            ::= {trapInstances 4}
            
            memoryPoor                              NOTIFICATION-TYPE
            STATUS                                  current
            DESCRIPTION
            ""
            ::= {trapInstances 5}
            
            wlanIfLinkUp                            NOTIFICATION-TYPE
            OBJECTS                                 {ifIndex}
            STATUS                                  current
            DESCRIPTION
            ""
            ::= {trapInstances 7}

            deauthenticateAttack                    NOTIFICATION-TYPE
            OBJECTS                                 {ifIndex}
            STATUS                                  current
            DESCRIPTION
            ""
            ::= {trapInstances 8}

            disassociateAttack                      NOTIFICATION-TYPE
            OBJECTS                                 {ifIndex}
            STATUS                                  current
            DESCRIPTION
            ""
            ::= {trapInstances 9}
            
            bcFlood                                 NOTIFICATION-TYPE
            OBJECTS                                 {ifIndex}
            STATUS                                  current
            DESCRIPTION
            ""
            ::= {trapInstances 10}

            webLogoutSuccessful                     NOTIFICATION-TYPE
            OBJECTS                                 {ifIndex}
            STATUS                                  current
            DESCRIPTION
            ""
            ::= {trapInstances 11}

            wlanIfLinkDown                          NOTIFICATION-TYPE
            OBJECTS                                 {ifIndex}
            STATUS                                  current
            DESCRIPTION
            ""
            ::= {trapInstances 13}

            stationAssocNotify                      NOTIFICATION-TYPE
            STATUS                                  current
            DESCRIPTION
            ""
            ::= {trapInstances 14}
            
            stationDisassocNotify                   NOTIFICATION-TYPE
            STATUS                                  current
            DESCRIPTION
            ""
            ::= {trapInstances 15}
            
            deAuthentication                   NOTIFICATION-TYPE
            STATUS                                  current
            DESCRIPTION
            ""
            ::= {trapInstances 20}
            


            miscellaneous                           OBJECT  IDENTIFIER ::= { dap2360B 6 }


     --       compatibilities                         OBJECT  IDENTIFIER ::= { miscellaneous 1 }

            END
